-- The Definition of Common Data Types follows

IN-CS2-datatypes {ccitt(0) identified-organization(4) etsi(0) inDomain(1) in-network(1) CS2(20) modules(0) in-cs2-datatypes (0) version1(0)}

DEFINITIONS IMPLICIT TAGS ::=
BEGIN
IMPORTS
	tc-Messages, classes FROM IN-CS2-object-identifiers	
		{ccitt(0) identified-organization(4) etsi(0) inDomain(1) in-network(1) CS2(20) module(0) in-cs2-object-identifiers(17) version1(0)}
	InvokeIdType
FROM TCAPMessages tc-Messages 
	EXTENSION,
		PARAMETERS-BOUND,
		SupportedExtensions {}
FROM IN-CS2-classes classes

	AddOnChargingInformation,
	ChargingTariffInformation
FROM Tarifing-DataTypes {itu-t(0) identified-organization etsi (0) 1296 version1(1)};


AccountNumber ::= NumericString (SIZE (1..151)) 
AChBillingChargingCharacteristics {PARAMETERS-BOUND : bound} ::= OCTET STRING (SIZE 
(bound.&minAChBillingChargingLength..bound.&maxAChBillingChargingLength))
-- The AChBillingChargingCharacteristics parameter specifies the charging related information
-- to be provided by the SSF and the conditions on which this information has to be reported
-- back to the SCF with the ApplyChargingReport operation.
-- Its content is network operator specific.
-- The internal structure of this parameter can be defined using ASN.1 and the related Basic
-- Encoding Rules (BER). In such a case the value of this paramter (after the first tag and length
-- information) is the BER encoding of the defined ASN.1 internal structure.
-- The tag of this parameter as defined by ETSI is never replaced.
-- Examples of charging related information to be provided by the SSF may be: bulk counter
-- values, costs, tariff change and time of charge, time stamps, durations, etc.
-- Examples of conditions on which the charging related information are to be reported may be: 
-- threshold value reached, timer expiration, tariff change, end of connection configuration, etc.

ActionIndicator  ::= ENUMERATED {
								activate 		(1),
								deactivate		(2),
								retrieve		(3)
								}
-- indicates the action to be performed by the ManageTriggerData operation (activate, deactivate
-- or retrieve the status of a TDP.

ActionPerformed  ::= ENUMERATED {
								activated		(1),
								deactivated		(2),
								alreadyActive	(3),
								alreadyInactive	(4),
								isActive		(5),
								isInactive		(6)
								}
-- indicates the result of the operation ManageTriggerData 
-- activated: response of activate TDP
-- deactivated: response of deactivate TDP
-- alreadyActive: response of activate TDP
-- alreadyInactive: response of deactivate TDP
-- isActive: response of retrieve status of TDP
-- isInactive: response of retrieve status of TDP

ActivableServices ::= BIT STRING {
	callingLineIdentificationPresentation 		(1),
	callingLineIdentificationRestriction 		(2),
	connectedLineIdentificationPresentation		(3),
	connectedLineIdentificationRestriction 		(4),
	callForwardingOnNoReply 					(5),
	callForwardingUnconditional 				(6),
	callForwardingOnBusy 						(7),
	callForwardingOnNotReachable 				(8),
	reverseCharging 							(9),
	adviceOfChargeOnStart 						(10),
	adviceOfChargeAtEnd 						(11),
	adviceOfChargeDuringCall 					(12),
	timeDependentRouting 						(13),
	callingPartingDependentRouting 				(14),
	outgoingCallBarring 						(15),
	incomingCallBarring 						(16)
	}
AdditionalCallingPartyNumber {PARAMETERS-BOUND : bound} 	::= Digits {bound}
-- Indicates the Additional Calling Party Number. 
-- Refer to ITU-T Recommendation Q.763 for encoding.
AlertingPattern 										::= OCTET STRING (SIZE(3))
-- Indicates a specific pattern that is used to alert a subscriber 
-- (e.g. distinctive ringing, tones, etc.). 
-- Only the trailing OCTET is used, the remaining OCTETS should be sent as NULL (zero)
-- The receiving side ignores the leading two OCTETS.
ApplicationTimer 										::=INTEGER (0..2047)
-- Used by the SCF to set a timer in the SSF. The timer is in seconds.
AssistingSSPIPRoutingAddress {PARAMETERS-BOUND : bound} 	::= Digits {bound}
-- Indicates the destination address of the SRF for the assist procedure.
BackwardGVNS {PARAMETERS-BOUND : bound} 					::= OCTET STRING (SIZE(
					bound.&minBackwardGVNSLength..bound.&maxBackwardGVNSLength))
-- Indicats the GVNS Backward information. Refer to Q.735, §6 for encoding.

BackwardServiceInteractionInd 		::= SEQUENCE {
				conferenceTreatmentIndicator		[1] OCTET STRING (SIZE(1))	OPTIONAL,
-- acceptConferenceRequest	'xxxx xx01'B
-- rejectConferenceRequest	'xxxx xx10'B
-- network default is accept conference request,
				callCompletionTreatmentIndicator	[2] OCTET STRING (SIZE(1))	OPTIONAL
-- acceptCallCompletionServiceRequest	'xxxx xx01'B,
-- rejectCallCompletionServiceRequest	'xxxx xx10'B
-- network default is accept call completion service request
				... 
				}


BCSMEvent {PARAMETERS-BOUND : bound} ::= SEQUENCE {
	eventTypeBCSM		[0] EventTypeBCSM,
	monitorMode			[1] MonitorMode,
	legID				[2] LegID	OPTIONAL,
	dpSpecificCriteria	[30] DpSpecificCriteria {bound}	OPTIONAL
	...	}
-- Indicates the BCSM Event information for monitoring.
BCUSMEvent 							::= SEQUENCE{
	eventType			[0] EventTypeBCUSM,
	monitorMode			[1] MonitorMode
	...
	}

BearerCapabilities 					::= BIT STRING {
	speech 					(0),
	bc64kbits 				(1),
	bc2x64kbits 			(2),
	bc384kbits 				(3),
	bc1536kbits 			(4),
	bc1920kbits 			(5),
	multirate 				(6),
	restrictedDigitalInfo	(7),
	bc3-1khzAudio 			(8),
	bc7khzAudio 			(9),
	video 					(10)
	}
BearerCapability {PARAMETERS-BOUND : bound} ::= CHOICE {
	bearerCap				[0] OCTET STRING (SIZE(2..bound.&maxBearerCapabilityLength)),
	tmr						[1] OCTET STRING (SIZE(1))
	}
-- Indicates the type of bearer capability connection to the user. For bearerCapability, either 
-- DSS1 (EN 300 403-1) or the ISUP User Service Information (ITU-T Recommendation Q.763)
-- encoding can be used. Refer 
-- to the ITU-T Recommendation Q.763 Transmission Medium Requirement parameter for tmr encoding.

BothwayThroughConnectionInd 		::= ENUMERATED {
	bothwayPathRequired		(0),
	bothwayPathNotRequired	(1)
	}
-- The default is as specified in EN 301 070-1

CallConditions {PARAMETERS-BOUND : bound} ::= CHOICE {
	userAbandon				[0] NULL,
	callFailure				[1] CauseValue,
	noReply					[2] INTEGER, -- time expressed in seconds
	callRelease				[3] NULL,
	ss-invocation			[4] InvokableService,
	creditLimitReached		[5] INTEGER,
	callDuration			[6] INTEGER,
	calledNumber			[7] NumberMatch {bound},
	answeredCall			[8] NULL
	}

CalledPartyBCDNumber {PARAMETERS-BOUND : bound} 	::= OCTET STRING (SIZE(
			bound.&minCalledPartyBCDNumberLength ..
			bound.&maxCalledPartyBCDNumberLength))
-- Indicates the Called Party Number, including service selection information. Refer to GSM 04.08 
-- for encoding. This data type carries only the "type of number", "numbering plan 
-- identification" and "number digit" fields defined in GSM 04.08; 
-- it does not carry the "called party 
-- BCD number IEI" or "length of called party BCD number contents".

CalledPartyNumber {PARAMETERS-BOUND : bound} 	::= OCTET STRING (SIZE
					(bound.&minCalledPartyNumberLength ..
bound.&maxCalledPartyNumberLength))
-- Indicates the Called Party Number. Refer to ITU-T Recommendation Q.763 for encoding.
CallIdentifier									::= INTEGER (1..2147483647)
CallingPartyBusinessGroupID {PARAMETERS-BOUND : bound} ::= OCTET STRING(SIZE(
			bound.&minCallingPartyBusinessGroupIDLength ..
			bound.&maxCallingPartyBusinessGroupIDLength))
-- Indicates the business group of the calling party. The value of this octet string is network 
-- operator specific.
CallingPartyNumber {PARAMETERS-BOUND : bound} 	::= OCTET STRING (SIZE (
			bound.&minCallingPartyNumberLength..
			bound.&maxCallingPartyNumberLength))
-- Indicates the Calling Party Number. Refer to ITU-T Recommendation Q.763 for encoding.
CallingPartySubaddress {PARAMETERS-BOUND : bound} ::= OCTET STRING(SIZE(
			bound.&minCallingPartySubAddressLength ..
			bound.&maxCallingPartySubAddressLength))

-- Indicates the Calling Party Subaddress. Refer to EN 300 403-1 for encoding.
CallingPartysCategory 						::= OCTET STRING (SIZE(1))
-- Indicates the type of calling party (e.g. operator, payphone, ordinary subscriber). 
-- Refer to ITU-T Recommendation Q.763 for encoding.

CallRecord {PARAMETERS-BOUND : bound} 		::= SEQUENCE {
	callDuration	 		[0] Duration, 
	callingPartyNumber		[1] CallingPartyNumber {bound}, 
	calledPartyNumber		[2] CalledPartyNumber {bound}
	... 
	}
CallResult {PARAMETERS-BOUND : bound} 		::= OCTET STRING (SIZE (bound.&minCallResultLength ..
			bound.&maxCallResultLength))

-- This parameter provides the SCF with the charging related information previously requested
-- using the ApplyCharging operation. This shall include the partyToCharge parameter as
-- received in the related ApplyCharging operation to correlate the result to the request
-- received in the related ApplyCharging operation to correlate the result to the request.
-- Its content is network operator specific.
-- The internal structure of this parameter can be defined using ASN.1 and the related Basic
-- Encoding Rules (BER). In such a case the value of this paramter (after the first tag and length
-- information) is the BER encoding of the defined ASN.1 internal structure.
-- The tag of this parameter as defined by ETSI is never replaced.
-- Examples of charging related information to be provided by the SSF may be: bulk counter values,
-- costs, tariff change and time of change, time stamps, durations, etc.
-- Examples of conditions on which the charging related information are to be reported may be: 
-- threshold value reached, timer expiration, tariff change, end of connection configuration, etc.
CallSegmentID {PARAMETERS-BOUND : bound} 	::= INTEGER (1..bound.&numOfCSs)
initialCallSegment INTEGER 					::= 1
-- the initial call segment represents the call segment that was there when the CSA was created, 
-- ie. the CS where
-- the trigger took place or the CS that was created by an InitateCallAttempt 
-- within a TC-BEGIN message.

Carrier {PARAMETERS-BOUND : bound} 			::= OCTET STRING(SIZE(
		bound.&minCarrierLength ..
		bound.&maxCarrierLength))
-- This parameter contains the carrier selection followed by Transit Network Selection.
-- The Carrier selection is one octet and is encoded as:
-- 00000000	No indication
-- 00000001	Selected carrier code pre-subscribed and not input by calling party
-- 00000010	Selected carrier identification code pre-subscribed and input by calling party
-- 00000011	Selected carrier identification code pre-subscribed, 
-- no indication of whether input by calling party.
-- 00000100 Selected carrier identification code not pre-subscribed and input by calling party
-- 00000101	}
-- to		}	spare
-- 11111110	}
-- 11111111	reserved
-- Refer to ITU-T Recommendation Q.763 for encoding of Transit Network Selection.

Cause {PARAMETERS-BOUND : bound} 			::= OCTET STRING (SIZE (minCauseLength..
		bound.&maxCauseLength))
-- Indicates the cause for interface related information. 
-- Refer to the ITU-T Recommendation Q.763 Cause parameter for encoding.
-- For the use of cause and location values refer to ITU-T Recommendation Q.850 
CauseValue 									::= OCTET STRING (SIZE (1)) 
--type extracted from Cause parameter in ITU-T Recommendation Q.763.
CGEncountered 								::= ENUMERATED {
	noCGencountered			(0),
	manualCGencountered		(1),
	scpOverload				(2)
	}
-- Indicates the type of automatic call gapping encountered, if any.
ChargingEvent {PARAMETERS-BOUND : bound} 	::= SEQUENCE {
	eventTypeCharging		[0] EventTypeCharging {bound},
	monitorMode				[1] MonitorMode,
	legID					[2] LegID			OPTIONAL,
	eventTypeTariff			[50[JMM1]] EventTypeTariff		OPTIONAL
	...
	}
-- This parameter indicates the charging event type and corresponding
-- monitor mode and LegID
ChargingParameters  {PARAMETERS-BOUND : bound} ::= SEQUENCE {
	unitsPerInterval		[0] INTEGER (0..bound.&maxUnitsPerInterval),
	timePerInterval			[1] INTEGER (0..bound.&maxTimePerInterval),
	scalingFactor			[2] INTEGER (0..bound.&maxScalingFactor),
	initialUnitIncrement	[3] INTEGER (0..bound.&maxInitialUnitIncrement) 	OPTIONAL,
	unitsPerDataInterval	[4] INTEGER (0..bound.&maxUnitsPerDataInterval) 	OPTIONAL,
	segmentsPerDataInterval	[5] INTEGER (0..bound.&maxSegmentsPerDataInterval)	OPTIONAL,
	initialTimeInterval		[6] INTEGER (0..bound.&maxInitialTimeInterval) 		OPTIONAL
	...
	}
CollectedDigits 							::= SEQUENCE {
	minimumNbOfDigits		[0] INTEGER (1..127)	DEFAULT 1,
	maximumNbOfDigits		[1] INTEGER (1..127),
	endOfReplyDigit			[2] OCTET STRING (SIZE (1..2))	OPTIONAL,
	cancelDigit				[3] OCTET STRING (SIZE (1..2))	OPTIONAL,
	startDigit				[4] OCTET STRING (SIZE (1..2))	OPTIONAL,
	firstDigitTimeOut		[5] INTEGER (1..127)			OPTIONAL,
	interDigitTimeOut		[6] INTEGER (1..127)			OPTIONAL,
	errorTreatment			[7] ErrorTreatment				DEFAULT reportErrorToScf,
	interruptableAnnInd		[8] BOOLEAN						DEFAULT TRUE,
	voiceInformation		[9] BOOLEAN						DEFAULT FALSE,
	voiceBack				[10] BOOLEAN					DEFAULT FALSE
	...
	}
-- The use of voiceBack is network operator specific.
-- The endOfReplyDigit, cancelDigit, and startDigit parameters have been designated as OCTET STRING, 
-- and are to be encoded as BCD, one digit per octet only, contained
-- in the four least significant bits of each OCTET. The usage is service dependent.
CollectedInfo 								::= CHOICE {
	collectedDigits			[0] CollectedDigits,
	iA5Information			[1] BOOLEAN
	}

ConnectedNumberTreatmentInd 				::= ENUMERATED {
	noINImpact				(0),
	presentationRestricted	(1),
	presentCalledINNumber	(2),
	presentCalledINNumberRestricted	(3)
	}
-- The default is as specified in EN 301 070-1.

Constraints 								::= SEQUENCE {
	maximumNumberOfDigits	[1] INTEGER (1..127),
	minimumNumberOfDigits	[2] INTEGER (1..127),
	typeOfRequestedInfo		[3] InfoType 					DEFAULT numericString,
	numberOfAllowedRetries	[4] INTEGER (0..127) 			DEFAULT 0
	...
	}

ControlType 								::= ENUMERATED {
	sCPOverloaded			(0),
	manuallyInitiated		(1),
	destinationOverload		(2)
	-- other values FOR FURTHER STUDY
	}

CorrelationID {PARAMETERS-BOUND : bound} 	::= Digits {bound}
-- used by SCF for correlation with a previous operation. 
-- Refer to clause 18 for a description of the procedures associated with this parameter.
CounterAndValue 							::= SEQUENCE {
		counterID			[0] CounterID,
		counterValue		[1] Integer4
		...
		}
CounterID 									::= INTEGER (0..99)
-- Indicates the counters to be incremented.
-- The counterIDs can be addressed by using the last digits of the dialed number.
CountersValue 								::= SEQUENCE SIZE(0..numOfCounters) OF CounterAndValue
Credit {PARAMETERS-BOUND : bound} 			::= CHOICE {
		currency	CurrencyValue {bound}, 
		units		CreditUnit
		}
CreditUnit 									::= INTEGER (0..maxCreditUnit) 
CriticalityType 							::= ENUMERATED {
		ignore				(0),
		abort				(1)
		} 
CSAID {PARAMETERS-BOUND : bound} 			::= INTEGER (1..bound.&numOfCSAs)
-- Indicates the SSF CSA identifier
CUApplicationInd							::= CHOICE{
	localValue				[0] INTEGER	,
	global					[1] OBJECT IDENTIFIER
	}
-- Parameter 'cUApplicationInd' identifies the triggered application. 
-- Possible applications: CCBS, CCNR, Q.SIG, etc.
CurrencyID 									::= PrintableString (SIZE (3)) -- ISO 639 code
CurrencyValue {PARAMETERS-BOUND : bound} 	::= SEQUENCE {
	currency	CurrencyID,
	amount		INTEGER (0..bound.&maxAmount)
	... 
	}
CutAndPaste 								::= INTEGER (0..22)
-- Indicates the number of digits to be deleted.

DateAndTime 								::= OCTET STRING (SIZE(6))
-- Indicates, amongst others, the start time for activate service filtering. Coded as YYMMDDHHMMSS
-- with each digit coded BCD. 
-- The first octet contains YY and the remaining items are sequenced following.
-- For example, 1993 September 30th, 12: 15: 01 would be encoded as: 
-- Bits 				HGFE		DCBA
-- leading octet		3			9
-- 						9			0
-- 						0			3
-- 						2			1
-- 						5			1
-- 						1			0
DestinationRoutingAddress {PARAMETERS-BOUND : bound} ::= SEQUENCE SIZE(1) OF
CalledPartyNumber {bound}
-- Indicates the Called Party Number.
Digits {PARAMETERS-BOUND : bound} 					::= OCTET STRING (SIZE
bound.&minDigitsLength..bound.&maxDigitsLength))
-- Indicates the address signalling digits. 
-- Refer to the ITU-T Recommendation Q.763 Generic Number & Generic Digits parameters for encoding. 
-- The coding of the subfields 'NumberQualifier' in Generic Number and 'TypeOfDigits' in
-- Generic Digits are irrelevant to the INAP;
-- the ASN.1 tags are sufficient to identify the parameter.
-- The ISUP format does not allow to exclude these subfields,
-- therefore the value is network operator specific.
-- The following parameters should use Generic Number: 
-- CorrelationID for AssistRequestInstructions, 
-- AssistingSSPIPRoutingAddress for EstablishTemporaryConnection,
-- calledAddressValue for all occurrences,callingAddressValue for all occurrences.
-- The following parameters should use Generic Digits: prefix, all 
-- other CorrelationID occurrences, dialledNumber filtering criteria, 
-- callingLineID filtering criteria, lineID for ResourceID
-- type, digitResponse for ReceivedInformationArg, 
-- iNServiceControlLow / iNServiceControlHighfor MidCallInfoType,
-- iNServiceControlCode for MidCallInfo.
DisplayInformation {PARAMETERS-BOUND : bound} 		::= IA5String (SIZE 
															(bound.&minDisplayInformationLength ..
															 bound.&maxDisplayInformationLength))
-- Indicates the display information.
-- Delivery of DisplayInformation parameter to Private Networks cannot be guaranteed 
-- due to signalling interworking problems, solutions are currently under study.
DpSpecificCriteria {PARAMETERS-BOUND : bound} 		::= CHOICE {
	numberOfDigits			[0] NumberOfDigits,
	applicationTimer		[1] ApplicationTimer,
	midCallControlInfo		[2] MidCallControlInfo {bound}
	}
 
-- The SCF may specify the number of digits to be collected by the SSF 
-- for the EventReportBCSMEvent event.
-- When all digits are collected, the SSF reports the event to the SCF.
-- The SCF may set a timer in the SSF for the No Answer event. If the user does not answer the call 
-- within the allotted time, the SSF reports the event to the SCF
Duration 											::= INTEGER (-2..86400)
-- Values are seconds

ElementaryMessageID ::= Integer4

Entry 												::=CHOICE {
	agreements				[0] OBJECT IDENTIFIER,
	networkSpecific			[1] Integer4
	}

ErrorTreatment 										::= ENUMERATED {
	reportErrorToScf		(0),
	help					(1),
	repeatPrompt			(2) 
	}
-- reportErrorToScf means returning the "ImproperCallerResponse" error in the event of an error
-- condition during collection of user info.
EventSpecificInformationBCSM {PARAMETERS-BOUND : bound} ::= CHOICE {
	collectedInfoSpecificInfo		[0] SEQUENCE {
			calledPartynumber		[0] CalledPartyNumber {bound},
			...
			},
	analysedInfoSpecificInfo		[1] SEQUENCE {
			calledPartynumber		[0] CalledPartyNumber {bound},
			...
			},
	routeSelectFailureSpecificInfo	[2] SEQUENCE {
			failureCause			[0] Cause {bound}			OPTIONAL,
			...
			},
	oCalledPartyBusySpecificInfo	[3] SEQUENCE {
			busyCause				[0] Cause {bound}			OPTIONAL,
			...
			},
	oNoAnswerSpecificInfo			[4] SEQUENCE {
-- no specific info defined --
			...
			},
	oAnswerSpecificInfo				[5] SEQUENCE {
			backwardGVNS			[0] BackwardGVNS {bound}	OPTIONAL,
			...
			},
	oMidCallSpecificInfo			[6] SEQUENCE {
			connectTime				[0] Integer4				OPTIONAL,
			oMidCallInfo			[1] MidCallInfo {bound} 	OPTIONAL,
			...
			},
	oDisconnectSpecificInfo	[7] SEQUENCE {
			releaseCause			[0] Cause {bound}			OPTIONAL,
			connectTime				[1] Integer4				OPTIONAL,
			 ...
			},
	tBusySpecificInfo [8] SEQUENCE {
			busyCause				[0] Cause {bound}			OPTIONAL,
			 ...
			},
	tNoAnswerSpecificInfo [9] SEQUENCE {
			-- no specific info defined --
			 ...
			},
	tAnswerSpecificInfo	[10] SEQUENCE {
			-- no specific info defined --
			...
			},
	tMidCallSpecificInfo [11] SEQUENCE {
			connectTime				[0] Integer4				OPTIONAL,
			tMidCallInfo			[1] MidCallInfo {bound} 	OPTIONAL,
			 ...
			},
	tDisconnectSpecificInfo	[12] SEQUENCE {
			releaseCause			[0] Cause {bound}			OPTIONAL,
			connectTime				[1] Integer4				OPTIONAL,
			 ...
			},
	oTermSeizedSpecificInfo	[13] SEQUENCE {
			-- no specific info defined 
			 ...
			},
	oSuspended	[14] SEQUENCE {
			-- no specific info defined 
			 ...
			},
	tSuspended	[15] SEQUENCE {
			-- no specific info defined 
			 ...
			},
	origAttemptAuthorized [16] SEQUENCE {
			-- no specific info defined 
			 ...
			},
	oReAnswer [17] SEQUENCE {
			-- no specific info defined 
			 ...
			},
	tReAnswer [18] SEQUENCE {
			-- no specific info defined 
			 ...
			},
	facilitySelectedAndAvailable [19] SEQUENCE {
			-- no specific info defined 
			 ...
			},
	callAccepted [20] SEQUENCE {
			-- no specific info defined 
			 ...
			},
	oAbandon [21] SEQUENCE {
			abandonCause			[0] Cause {bound}			OPTIONAL,
			...
			},
	tAbandon	[22] SEQUENCE {
			abandonCause			[0] Cause {bound}			OPTIONAL,
			...
			},
	terminationAttemptAuthorized [24] SEQUENCE {
			-- no specific info defined 
			 ...
			}
	}

-- Indicates the call related information specific to the event.
-- The connectTime indicates the duration between the received answer indication 
-- from the called party side
-- and the release of the connection for ODisconnect, OException, TDisconnect, or TException 
-- or between
-- the received answer indication from the called party side and the time
-- of detection of the required mid call event.
-- The unit for the connectTime is 100 milliseconds.

EventSpecificInformationBCUSM {PARAMETERS-BOUND : bound} ::= CHOICE{

componentRecievedSpecificInfo	[0]	SEQUENCE {
componentReceivedInfo			[0]	OCTET STRING
{SIZE (bound.&minCompReceivedInforLen
..bound.&maxCompRecievedInfoLen)					OPTIONAL,
-- Its content is network signalling/operator specific.
-- The internal structure of this parameter can be defined using ASN.1 and the related Basic
-- Encoding Rules (BER). In such a case the value of this paramter (after the first tag and length
-- information) is the BER encoding of the defined ASN.1 internal structure.
-- The tag of this parameter as defined by ETSI is never replaced.
...
},
	associationReleaseRequestedSpecificInfo [1] SEQUENCE{
		associationReleaseInfo			[0] OCTET STRING
			(SIZE(bound.&minAssReleaseInfoLength
			     ..bound.&maxAssReleaseInfoLength)				OPTIONAL,
-- Its content is network signalling/operator specific.
-- The internal structure of this parameter can be defined using ASN.1 and the related Basic
-- Encoding Rules (BER). In such a case the value of this paramter (after the first tag and length
-- information) is the BER encoding of the defined ASN.1 internal structure.
-- The tag of this parameter as defined by ETSI is never replaced.
		releaseCause					[1] Cause {bound}		OPTIONAL,
		...
		}
	}
EventSpecificInformationCharging {PARAMETERS-BOUND : bound} ::= OCTET STRING (SIZE 
							(bound.&minEventSpecificInformationChargingLength..
			bound.&maxEventSpecificInformationChargingLength))
-- Its content is network signalling/operator specific.
-- The internal structure of this parameter can be defined using ASN.1 and the related Basic
-- Encoding Rules (BER). In such a case the value of this paramter (after the first tag and length
-- information) is the BER encoding of the defined ASN.1 internal structure.
-- The tag of this parameter as defined by ETSI is never replaced.
-- Indicates the charging related information specific to the event.
-- An example data type definition for this parameter is given below: 
--		chargePulses					[0] Integer4,
--		chargeMessages					[1] OCTET STRING (SIZE (min..max))
EventTypeBCSM 										::= ENUMERATED {
	origAttemptAuthorized			(1),
	collectedInfo					(2),
	analysedInformation				(3),
	routeSelectFailure				(4),
	oCalledPartyBusy				(5),
	oNoAnswer						(6),
	oAnswer							(7),
	oMidCall						(8),
	oDisconnect						(9),
	oAbandon						(10),
	termAttemptAuthorized			(12),
	tBusy							(13),
	tNoAnswer						(14),
	tAnswer							(15),
	tMidCall						(16),
	tDisconnect						(17),
	tAbandon						(18),
	oTermSeized						(19),
	oSuspended						(20),
	tSuspended						(21),
	origAttempt						(22),
	termAttempt						(23),
	oReAnswer						(24),
	tReAnswer						(25),
	facilitySelectedAndAvailable	(26),
	callAccepted					(27)
	}

-- Indicates the BCSM detection point event. 
-- Refer to Q.1224 for additional information on the events.
-- Values origAttempt and termAttempt can only be used for TDPs

EventTypeBCUSM 										::= ENUMERATED{
	componentReceived				(127),
	associationReleaseRequested		(126),
	activationReceivedAndAuthorized	(125)
	}

EventTypeCharging {PARAMETERS-BOUND : bound} 		::= OCTET STRING (SIZE (
							bound.&minEventTypeChargingLength..
							bound.&maxEventTypeChargingLength))
-- This parameter indicates the charging event type.
-- Its content is network signalling/operator specific.
-- The internal structure of this parameter can be defined using ASN.1 and the related Basic
-- Encoding Rules (BER). In such a case the value of this paramter (after the first tag and length
-- information) is the BER encoding of the defined ASN.1 internal structure.
-- The tag of this parameter as defined by ETSI is never replaced.
-- An example data type definition for this parameter is given below: 
-- EventTypeCharging 								::= ENUMERATED {
-- 		chargePulses 				(0),
-- 		chargeMessages 				(1)
-- 				}
EventTypeTariff 									::= ENUMERATED {
	chargingTariffInformation		(0),
	addOnchargingInformation		(1),
	chargingAcknowledgementInformation	(2),
	chargingAcknowledgeTimerExpired	(3)
	}
ExtensionField {PARAMETERS-BOUND : bound} 			::= SEQUENCE{
	type	EXTENSION.&id ({SupportedExtensions {bound}}),
			-- shall identify the value of an EXTENSION type
	criticality	CriticalityType									DEFAULT ignore,
	value					[1] EXTENSION.&ExtensionType 	
				({SupportedExtensions {bound}}{@type}),
...
	}
--This parameter indicates an extension of an argument data type. 
-- Its content is network operator specific

FacilityGroup										::= CHOICE {
	trunkGroupID			[0] INTEGER,
	privateFacilityID		[1] INTEGER,
	huntGroup				[2] OCTET STRING,
	routeIndex				[3] OCTET STRING
	}
-- Indicates the particular group of facilities to route the call. 
-- huntGroup and routeIndex are encoded as 
-- network operator specific.

FCIBillingChargingCharacteristics {PARAMETERS-BOUND : bound} ::= CHOICE {
	fCIBCCcs1	OCTET STRING (SIZE (bound.&minFCIBCcs1Length..
									bound.&maxFCIbccCS1Length)),
-- Its content is network operator specific.
-- The internal structure of this parameter can be defined using ASN.1 and the related Basic
-- Encoding Rules (BER). In such a case the value of this paramter (after the first tag and length
-- information) is the BER encoding of the defined ASN.1 internal structure.
-- The tag of this parameter as defined by ETSI is never replaced.
	fCIBCCsequencecs2		[51] SEQUENCE {
		fCIBCC					[0] OCTET STRING (SIZE (bound.&minFCIbccCS2Length ..
														bound.&maxFCIbccCS2Length))	OPTIONAL,
-- Its content is network operator specific.
-- The internal structure of this parameter can be defined using ASN.1 and the related Basic
-- Encoding Rules (BER). In such a case the value of this paramter (after the first tag and length
-- information) is the BER encoding of the defined ASN.1 internal structure.
-- The tag of this parameter as defined by ETSI is never replaced.
		tariff					[1] CHOICE {
			crgt					[0] ChargingTariffInformation,
			aocrg					[1] AddOnChargingInformation
			} 													OPTIONAL,
...
		}
	}

-- This parameter indicates the billing and/or charging characteristics. 
-- Its content is network operator specific.
-- An example datatype definition for this parameter is given below: 
-- FCIBillingChargingCharacteristics ::= CHOICE {
-- 	completeChargingrecord		[0] OCTET STRING (SIZE (min..max)),
--	correlationID				[1] CorrelationID,
--	scenario2Dot3				[2] SEQUENCE {
--		chargeParty					[0] LegID 								OPTIONAL,
--		chargeLevel					[1] OCTET STRING (SIZE (min..max))		OPTIONAL,
--		chargeItems					[2] SET OF Attribute					OPTIONAL
--		}
--	}
FilteredCallTreatment {PARAMETERS-BOUND : bound} 	::= SEQUENCE {
	sFBillingChargingCharacteristics	[0] SFBillingChargingCharacteristics {bound},
	informationToSend					[1] InformationToSend {bound}		OPTIONAL,
	maximumNumberOfCounters				[2] MaximumNumberOfCounters			OPTIONAL,
	releaseCause						[3] Cause {bound}					OPTIONAL,
	sFTariffMessage						[50] CHOICE {
		crgt								[0] ChargingTariffInformation}		OPTIONAL,
...
	}
-- If releaseCause is not present, the default value is the same as the ISUP cause value decimal 31.
-- If informationToSend is present, the call will be released after the end of the announcement 
-- with the indicated or default releaseCause.
-- If maximumNumberOfCounters is not present, ServiceFilteringResponse will be sent with 
-- CountersValue ::= SEQUENCE SIZE (0) OF CountersAndValue
FilteringCharacteristics 							::= CHOICE {
	interval				[0] INTEGER (-1..32000),
	numberOfCalls			[1] Integer4
	}
-- Indicates the severity of the filtering and the point in time when 
-- the ServiceFilteringResponse is to be sent. 
-- If = interval, every interval of time the next call leads to an InitialDP
-- and a ServiceFilteringResponse is sent to 
-- the SCF. The interval is specified in seconds.
-- If = NumberOfCalls, every N calls the Nth call leads to an InitialDP 
-- and a ServiceFilteringResponse is sent to the SCF.
-- If ActivateServiceFiltering implies several counters - filtering on several dialled numbers -,
-- the numberOfCalls would include calls to all the dialled numbers.
FilteringCriteria {PARAMETERS-BOUND : bound} 	::= CHOICE {
	serviceKey				[2] ServiceKey,
	addressAndService		[30] SEQUENCE {
		calledAddressValue	[0] Digits {bound},
		serviceKey			[1] ServiceKey,
		callingAddressValue	[2] Digits {bound}							OPTIONAL,
		locationNumber		[3] LocationNumber {bound}					OPTIONAL,
	...
		}
	}
-- In case calledAddressValue is specified, the numbers to be filtered are from calledAddressValue
-- up to and including calledAddressValue + maximumNumberOfCounters-1.
-- The last two digits of calledAddressvalue can not exceed 100-maximumNumberOfCounters.
FilteringTimeOut 									::= CHOICE {
	duration				[0] Duration,
	stopTime				[1] DateAndTime
	}
-- Indicates the maximum duration of the filtering. 
-- When the timer expires, a ServiceFilteringResponse is sent to the SCF.
ForwardCallIndicators 								::= OCTET STRING (SIZE(2))
-- Indicates the Forward Call Indicators. Refer to ITU-T Recommendation Q.763 for encoding
ForwardGVNS {PARAMETERS-BOUND : bound} 				::= OCTET STRING (SIZE(
			bound.&minForwardGVNSLength..
			bound.&maxForwardGVNSLength))
-- Indicats the GVNS Forward information. Refer to Q.735, §6 for encoding.
ForwardServiceInteractionInd						 ::= SEQUENCE {
	conferenceTreatmentIndicator	[1] OCTET STRING (SIZE(1))			OPTIONAL,
	-- acceptConferenceRequest	'xxxx xx01'B
	-- rejectConferenceRequest	'xxxx xx10'B
	-- network default is accept conference request
	callDiversionTreatmentIndicator	[2] OCTET STRING (SIZE(1))			OPTIONAL,
	-- callDiversionAllowed		'xxxx xx01'B
	-- callDiversionNotAllowed	'xxxx xx10'B
	-- network default is Call Diversion allowed
	callOfferingTreatmentIndicator	[3] OCTET STRING (SIZE(1))			OPTIONAL, 
	-- callOfferingNotAllowed	'xxxx xx01'B,
	-- callOfferingAllowed		'xxxx xx10'B
	-- network default is Call Offering not allowed
	callingPartyRestrictionIndicator	[4] OCTET STRING (SIZE(1))		OPTIONAL,
	-- noINImpact				'xxxx xx01'B,
	-- presentationRestricted	'xxxx xx10'B
	-- network default is noINImpact
...
	}

GapCriteria {PARAMETERS-BOUND : bound} 				::= CHOICE {
	calledAddressValue			[0] Digits {bound},
	gapOnService				[2] GapOnService,
	gapAllInTraffic				[3] NULL,
	calledAddressAndService		[29] SEQUENCE {
		calledAddressValue			[0] Digits {bound},
		serviceKey					[1] ServiceKey
		},
	callingAddressAndService	[30] SEQUENCE {
		callingAddressValue			[0] Digits {bound},
		serviceKey					[1] ServiceKey,
		locationNumber				[2] LocationNumber {bound}			OPTIONAL,
	...
		}
	}
-- Both calledAddressValue and callingAddressValue can be
-- incomplete numbers, in the sense that a limited amount of digits can be given.

-- For the handling of numbers starting with the same digit string refer to the detailed procedure
-- of the CallGap operation
GapOnService 										::= SEQUENCE {
	serviceKey				[0] ServiceKey,
...
	}
GapIndicators 										::= SEQUENCE {
	duration				[0] Duration,
	gapInterval				[1] Interval,
...
	}
-- Indicates the gapping characteristics. 
-- No gapping when gapInterval equals 0, and gap all calls when gapInterval equals -1.
GapTreatment {PARAMETERS-BOUND : bound} 				::= CHOICE {
	informationToSend		[0] InformationToSend {bound},
	releaseCause			[1] Cause {bound},
	both					[2] SEQUENCE {
		informationToSend		[0] InformationToSend {bound},
		releaseCause			[1] Cause {bound},
	...
		}
	}
-- The default value for Cause is the same as in ISUP.
GenericName {PARAMETERS-BOUND : bound} 				::= OCTET STRING (SIZE(
				bound.&minGenericNameLength..
				bound.&maxGenericNameLength))
-- Refer to EN 300 403-1 Display Information for encoding.
GenericNumber {PARAMETERS-BOUND : bound} 			::= OCTET STRING (SIZE(
				bound.&minGenericNumberLength..
				bound.&maxGenericNumberLength))
-- Refer to ITU-T Recommendation Q.763 Generic Number for encoding.
GenericNumbers {PARAMETERS-BOUND : bound} 			::= SET SIZE(1..bound.&numOfGenericNumbers) OF GenericNumber {bound}
HighLayerCompatibilities 							::= BIT STRING {
	telephony 				(0),
	facsimileGroup2-3 		(1),
	facsimileGroup4classeI 	(2),
	teletexMixedMode 		(3),
	teletexProcessableMode 	(4),
	teletexBasicMode 		(5),
	syntaxBasedVideotex 	(6),
	internationalVideotex 	(7),
	telexService 			(8),
	messageHandlingSystem 	(9),
	osiApplication 			(10),
	audioVisual 			(11)
	}
HighLayerCompatibility 						::= OCTET STRING (SIZE (highLayerCompatibilityLength))
-- Indicates the teleservice. For encoding, DSS1 (EN 300 403-1) is used.
InbandInfo {PARAMETERS-BOUND : bound} 				::= SEQUENCE {
	messageID				[0] MessageID {bound},
	numberOfRepetitions		[1] INTEGER (1..127)							OPTIONAL,
	duration				[2] INTEGER (0..32767)							OPTIONAL,
	interval				[3] INTEGER (0.. 32767)							OPTIONAL.
...
	}
-- Interval is the time in seconds between each repeated announcement. Duration is the total
-- amount of time in seconds, including repetitions and intervals.
-- The end of announcement is either the end of duration or numberOfRepetitions, 
-- whatever comes first.
-- duration with value 0 indicates infinite duration
InformationToRecord {PARAMETERS-BOUND : bound} 		::= SEQUENCE {
	messageID				[0] ElementaryMessageID	OPTIONAL,
	messageDeletionTimeOut	[1] INTEGER (1..3600)	OPTIONAL,
-- Time units = hours
	timeToRecord			[3] INTEGER (0..bound.&maxRecordingTime)		OPTIONAL,
-- Time units = seconds
		controlDigits		[4] SEQUENCE {
			endOfRecordingDigit		[0] OCTET STRING (SIZE(1..2))			OPTIONAL,
			cancelDigit				[1] OCTET STRING (SIZE(1..2))			OPTIONAL,
			replayDigit				[2] OCTET STRING (SIZE(1..2))			OPTIONAL,
			restartRecordingDigit	[3] OCTET STRING (SIZE(1..2))			OPTIONAL,
			restartAllowed			[4] BOOLEAN 							DEFAULT FALSE,
			replayAllowed			[5] BOOLEAN 							DEFAULT FALSE.
	...
			},
	...
		}
InformationToSend {PARAMETERS-BOUND : bound} 		::= CHOICE {
	inbandInfo				[0] InbandInfo {bound},
	tone					[1] Tone,
	displayInformation		[2] DisplayInformation {bound}
	}
InfoToSend {PARAMETERS-BOUND : bound} 				::= CHOICE {
	messageID				[0] MessageID {bound},
	toneId					[1] ToneId,
	displayInformation		[2] DisplayInformation {bound}
	}
InfoType 											::= ENUMERATED {
	numericString 		(0),
	characterString 	(1),
	iA5String 			(2)
	}
INServiceCompatibilityIndication {PARAMETERS-BOUND : bound} ::= SEQUENCE SIZE (1..bound.&numOfInServiceCompatibilityIndLength) OF Entry
INServiceCompatibilityResponse	 					::= Entry
Integer4 											::= INTEGER (0..2147483647)
Interval 											::= INTEGER (-1..60000)
-- Units are milliseconds.
InvokableService 									::= ENUMERATED {
	callingLineIdentificationRestriction 	(1),
	connectedLineIdentificationRestriction 	(2),
	callWaiting 							(3),
	callHold 								(4),
	reverseCharging 						(5),
	explicitCallTransfer 					(6),
	callCompletionOnBusySubscriber 			(7)
	}
InvokeID 											::= InvokeIdType
-- Operation invoke identifier.
IPAvailable {PARAMETERS-BOUND : bound} 				::= OCTET STRING (SIZE (
			bound.&minIPAvailableLength..bound.&maxIPAvailableLength))
-- Its content is network operator specific.
-- The internal structure of this parameter can be defined using ASN.1 and the related Basic
-- Encoding Rules (BER). In such a case the value of this paramter (after the first tag and length
-- information) is the BER encoding of the defined ASN.1 internal structure.
-- The tag of this parameter as defined by ETSI is never replaced.
-- Indicates that the resource is available.
IPRoutingAddress {PARAMETERS-BOUND : bound} 			::= CalledPartyNumber {bound}
-- Indicates the routing address for the IP.
IPSSPCapabilities {PARAMETERS-BOUND : bound} 		::= OCTET STRING (SIZE (
			bound.&minIPSSPCapabilitiesLength..bound.&maxIPSSPCapabilitiesLength))
-- Its content is network operator specific.
-- The internal structure of this parameter can be defined using ASN.1 and the related Basic
-- Encoding Rules (BER). In such a case the value of this paramter (after the first tag and length
-- information) is the BER encoding of the defined ASN.1 internal structure.
-- The tag of this parameter as defined by ETSI is never replaced.
-- Indicates the SRF resources available at the SSP.
ISDNAccessRelatedInformation {PARAMETERS-BOUND : bound} ::= OCTET STRING(SIZE(
			bound.&minISDNAccessRelatedInformationLength ..
			bound.&maxISDNAccessRelatedInformationLength))

-- Indicates the destination user network interface related information. 
-- Refer to the ITU-T Recommendation Q.763 Access 
-- Transport parameter for encoding.
Language 											::= PrintableString (SIZE (3)) 
-- ISO 639 codes only; 

LegID 												::= CHOICE {
	sendingSideID			[0] LegType,
	receivingSideID			[1] LegType
	}
-- Indicates a reference to a specific party in a call. 
-- OPTIONAL denotes network operator specific use 
-- with a choice of unilateral ID assignment or bilateral ID assignment.
-- OPTIONAL for LegID also denotes the following: 
-- when only one party exists in the call, this parameter is not needed (as no ambiguity exists);
-- when more than one party exists in the call, one of the following alternatives applies: 
--	 1. LegID is present and indicates which party is concerned.
--	 2. LegID is not present and a default value is assumed (e.g. calling party in the case of the 
--	  ApplyCharging operation).
-- Choice between these two alternatives is kept a network operator option.
LegType 											::= OCTET STRING (SIZE(1))
leg1 LegType 										::= '01'H
leg2 LegType 										::= '02'H
LocationNumber {PARAMETERS-BOUND : bound} 			::= OCTET STRING (SIZE (
			bound.&minLocationNumberLength..
			bound.&maxLocationNumberLength))
-- Indicates the Location Number for the calling party. 
-- Refer to ITU-T Recommendation Q.763 (White book) for encoding.
MailBoxID {PARAMETERS-BOUND : bound} 				::= OCTET STRING (SIZE(
				bound.&minMailBoxIDLength..bound.&maxMailBoxIDLength))
-- Its content is network operator specific.
-- The internal structure of this parameter can be defined using ASN.1 and the related Basic
-- Encoding Rules (BER). In such a case the value of this paramter (after the first tag and length
-- information) is the BER encoding of the defined ASN.1 internal structure.
-- The tag of this parameter as defined by ETSI is never replaced.
MaximumNumberOfCounters 							::= INTEGER (1..numOfCounters)
Media 												::= ENUMERATED {
	voiceMail 				(0),
	faxGroup3 				(1),
	faxGroup4 				(2)
	}

MessageID {PARAMETERS-BOUND : bound} 				::= CHOICE {
	elementaryMessageID		[0] Integer4,
	text					[1] SEQUENCE {
		messageContent			[0] IA5String (SIZE
								 (bound.&minMessageContentLength..bound.&maxMessageContentLength)),
		attributes				[1] OCTET STRING (SIZE
								 (bound.&minAttributesLength..bound.&maxAttributesLength)) OPTIONAL,
-- Its content is network operator specific.
-- The internal structure of this parameter can be defined using ASN.1 and the related Basic
-- Encoding Rules (BER). In such a case the value of this paramter (after the first tag and length
-- information) is the BER encoding of the defined ASN.1 internal structure.
-- The tag of this parameter as defined by ETSI is never replaced.
...
	},
	elementaryMessageIDs	[29] SEQUENCE SIZE (1.. bound.&numOfMessageIDs) OF Integer4,
	variableMessage			[30] SEQUENCE {
		elementaryMessageID		[0] Integer4,
		variableParts			[1] SEQUENCE SIZE (1..5) OF VariablePart {bound},
		...
		}
	}
-- OPTIONAL denotes network operator specific use.
MidCallControlInfo {PARAMETERS-BOUND : bound} 		::= SEQUENCE SIZE (
	bound.&minMidCallControlInfoNum .. 
	bound.&maxMidCallControlInfoNum) OF SEQUENCE {
		midCallInfoType		[0]	MidCallInfoType {bound},
		midCallReportType	[1]	ENUMERATED {
			inMonitoringState	(0),
			inAnyState			(1)
			} 														DEFAULT inMonitoringState,
		...
		}
MidCallInfo {PARAMETERS-BOUND : bound} 				::= SEQUENCE {
	iNServiceControlCode	[0] Digits {bound},
...
	}
MidCallInfoType {PARAMETERS-BOUND : bound}			::= SEQUENCE {
	iNServiceControlCodeLow		[0] Digits {bound},
	iNServiceControlCodeHigh	[1] Digits {bound}	OPTIONAL,
...
	}
MiscCallInfo 										::= SEQUENCE {
	messageType				[0] ENUMERATED {
		request					(0),
		notification			(1),
	...
		}
	}
-- Indicates detection point related information.
MonitorMode	 										::= ENUMERATED {
	interrupted					(0),
	notifyAndContinue			(1),
	transparent					(2)
	}
-- Indicates the event is relayed and/or processed by the SSP.
-- If this parameter is used in the context of charging events, 
-- the following definitions apply for the handling of charging events: 
-- Interrupted means that the SSF notifies the SCF of the charging event using
-- EventNotificationCharging, does not process the event but discard it.
-- NotifyAndContinue means that SSF notifies the SCF of the charging event using
-- EventNotificationCharging, and continues processing the event or signal without 
-- waiting for SCF instructions.
-- Transparent means that the SSF does not notify the SCF of the event. 
-- This value is used to end the monitoring of a previously requested charging event.
-- Previously requested charging events are monitored
-- until ended by a transparent monitor mode, or until the end of the connection configuration.
-- For the use of this parameter in the context of BCSM events refer to clause 18.
Notification 										::= ENUMERATED {
	userAbandon 				(0),
	callFailure 				(1),
	noReply						(2),
	callRelease 				(3),
	ssInvocation 				(4),
	creditLimitReached 			(5),
	callDuration 				(6),
	calledNumber 				(7),
	answeredCall 				(8)
	}
NotificationInformation {PARAMETERS-BOUND : bound} ::= CHOICE {
	userAbandonSpecificInfo		[0] SEQUENCE {...},
	callFailureSpecificInfo			[1] SEQUENCE {
		failureCause				[0] Cause {bound}				OPTIONAL,
		...},
	noReplySpecificInfo			[2] SEQUENCE {...},
	callReleaseSpecificInfo		[3] SEQUENCE {
		releaseCause				[0] Cause {bound}				OPTIONAL,
		timeStamp					[1] DateAndTime					OPTIONAL, 
		...},
	ssInvocationSpecificInfo	[4] SEQUENCE {
		invokedService				[0] InvokableService,
		...},
	creditLimitReachedSpecificInfo	[5] SEQUENCE {
		timeStamp					[0] DateAndTime					OPTIONAL,
		...},
	callDurationSpecificInfo	[6] SEQUENCE {
		timeStamp					[0] DateAndTime					OPTIONAL,
		...},
	calledNumberSpecificInfo	[7] SEQUENCE {
		calledNumber				[0] CalledPartyNumber {bound}	OPTIONAL,
		...},
	answeredCallSpecificInfo	[8] SEQUENCE {
		timeStamp					[0] DateAndTime					OPTIONAL,
		...}
	}
NumberMatch	{PARAMETERS-BOUND : bound}	 			::=	CHOICE {
initialMatch				[0] CalledPartyNumber {bound},
totalMatch					[1]	CalledPartyNumber {bound}
}
NumberOfDigits 										::= INTEGER (1..255)
-- Indicates the number of digits to be collected

OCSIApplicacable 									::= NULL
-- Indicates that the OCSI, if present, shall be applied on the outgoing call leg created with 
-- a Connect operation
OperationCode 										::= CHOICE {
	globalCode			OBJECT IDENTIFIER,
	local				INTEGER
	}
-- contains the operation value, or error value (object identifier), or problem value of 
-- the FACILITY IE, and the argument, the result, or the reject part of the same FACILITY IE 
-- that is received with DSS1 message from the user. (See Q.932 8.2.2 for encoring.)

OriginalCalledPartyID {PARAMETERS-BOUND : bound} 	::= OCTET STRING (SIZE(
			bound.&minOriginalCalledPartyIDLength..bound.&maxOriginalCalledPartyIDLength)) 
-- Indicates the original called number. 
-- Refer to the ITU-T Recommendation Q.763 Original Called Number for encoding.
ProfileIdentifier {PARAMETERS-BOUND : bound}		::= CHOICE {
	access					[0] CalledPartyNumber {bound},
	group					[1] FacilityGroup
	}
-- Note that 'CalledPartyNumber' is used to address a subscriber access line.
-- The data type was reused from the existing types to avoid the definition of a new one.

Reason {PARAMETERS-BOUND : bound} 					::= OCTET STRING (SIZE(
		bound.&minReasonLength..bound.&maxReasonLength))
-- Its content is network operator specific.
-- The internal structure of this parameter can be defined using ASN.1 and the related Basic
-- Encoding Rules (BER). In such a case the value of this paramter (after the first tag and length
-- information) is the BER encoding of the defined ASN.1 internal structure.
-- The tag of this parameter as defined by ETSI is never replaced.
ReceivedInformation {PARAMETERS-BOUND : bound} 		::= SEQUENCE SIZE (
			bound.&minReceivedInformationLength.. bound.&maxReceivedInformationLength) OF IA5String 
ReceivedStatus 										::=ENUMERATED {
	messageComplete 		(0),
	messageInterrupted 		(1),
	messageTimeOut 			(2)
	}
RecordedMessageID 									::= Integer4 
RedirectingPartyID {PARAMETERS-BOUND : bound} 		::= OCTET STRING (SIZE (
			bound.&minRedirectingPartyIDLength.. bound.&maxRedirectingPartyIDLength))
-- Indicates redirecting number. 
-- Refer to the ITU-T Recommendation Q.763 Redirecting number for encoding.
RedirectionInformation 								::= OCTET STRING (SIZE(2))
-- Indicates redirection information. Refer to the ITU-T Recommendation Q.763 [20] Redirection Information for encoding.
RegistratorIdentifier {PARAMETERS-BOUND : bound} 	::= OCTET STRING(SIZE(
			bound.&min RegistratorIdentifierLength.. bound.&max RegistratorIdentifierLength))
-- Its content is network operator specific.
-- The internal structure of this parameter can be defined using ASN.1 and the related Basic
-- Encoding Rules (BER). In such a case the value of this paramter (after the first tag and length
-- information) is the BER encoding of the defined ASN.1 internal structure.
-- The tag of this parameter as defined by ETSI is never replaced.


RequestedInformationList {PARAMETERS-BOUND : bound} 	::= SEQUENCE SIZE (1..numOfInfoItems) OF RequestedInformation {bound}
RequestedInformationTypeList 						::= SEQUENCE SIZE (1..numOfInfoItems) OF RequestedInformationType
RequestedInformation {PARAMETERS-BOUND : bound} 		::= SEQUENCE {
	requestedInformationType	[0] RequestedInformationType,
	requestedInformationValue	[1] RequestedInformationValue {bound},
...
	}
RequestedInformationType 							::= ENUMERATED {
	callAttemptElapsedTime		(0),
	callStopTime				(1),
	callConnectedElapsedTime	(2),
	calledAddress				(3),
	releaseCause				(30)
	}
RequestedInformationValue {PARAMETERS-BOUND : bound} ::= CHOICE {
	callAttemptElapsedTimeValue		[0] INTEGER (0..255),
	callStopTimeValue				[1] DateAndTime,
	callConnectedElapsedTimeValue	[2] Integer4,
	calledAddressValue				[3] Digits {bound},
	releaseCauseValue				[30] Cause {bound}
	}

-- The callAttemptElapsedTimeValue is specified in seconds. The unit for the
-- callConnectedElapsedTimeValue is 100 milliseconds
RequestedNotifications {PARAMETERS-BOUND : bound} 	::= SET OF CallConditions {bound}
RequestedType 										::= INTEGER (0 .. 127) 
RequestedUTSI {PARAMETERS-BOUND : bound} 			::= SEQUENCE {
	uSIServiceIndicator			[0] USIServiceIndicator {bound},
	uSImonitorMode				[1] USIMonitorMode,
...
	}

RequestedUTSIList {PARAMETERS-BOUND : bound} 		::= SEQUENCE SIZE (bound.&minRequestedUTSINum..
			bound.&maxRequestedUTSINum) OF RequestedUTSI {bound}

ResponseCondition 									::= ENUMERATED {
	intermediateResponse		(0),
	lastResponse				(1)
-- additional values are for further study
	}
-- ResponseCondition is used to identify the reason why ServiceFilteringResponse operation is sent.
-- intermediateresponse identifies that service filtering is running and the interval time is 
-- expired and a call is received, or that service filtering is running and the threshold value 
-- is reached.
-- lastResponse identifies that the duration time is expired and service filtering has been finished
-- or that the stop time is met and service filtering has been finished.
RouteList {PARAMETERS-BOUND : bound} 				::= SEQUENCE SIZE(1..3) OF OCTET STRING (SIZE 
			(bound.&minRouteListLength..bound.&maxRouteListLength))
-- Indicates a list of trunk groups or a route index. See Q.1224 for additional information on this item.
RoutingAddress {PARAMETERS-BOUND : bound} 			::= CHOICE {
	routingProhibited			[0] NULL,
	destinationRoutingAddress	[1] DestinationRoutingAddress {bound}
	}
ScfAddress {PARAMETERS-BOUND : bound} 				::= OCTET STRING (SIZE 
			(bound.&minScfAddressLength..bound.&maxScfAddressLength))
-- ISDN address 
ScfID {PARAMETERS-BOUND : bound} 					::= OCTET STRING (SIZE 
			(bound.&minScfIDLength..bound.&maxScfIDLength))
-- defined by network operator.
-- Indicates the SCF identity.
-- Used to derive the INAP address of the SCF to establish a connection between a requesting FE
-- and the specified SCF.
-- When ScfID is used in an operation which may cross an internetwork boundary, its encoding must
-- be understood in both networks; this requires bilateral agreement on the encoding.
-- Refer to 3.5/ETS 300 009-1 "calling party address" parameter for encoding. It indicates the SCCP address of the SCF.
-- Other encoding schemes are also possible as an operator specific option.
SCIBillingChargingCharacteristics {PARAMETERS-BOUND : bound} ::= OCTET STRING (SIZE (
			bound.&minSCIBillingChargingLength..
			bound.&maxSCIBillingChargingLength))
-- This parameter indicates the billing and/or charging characteristics.
-- Its content is network signalling/operator specific.
-- The internal structure of this parameter can be defined using ASN.1 and the related Basic
-- Encoding Rules (BER). In such a case the value of this paramter (after the first tag and length
-- information) is the BER encoding of the defined ASN.1 internal structure.
-- The tag of this parameter as defined by ETSI is never replaced.
-- An example datatype definition for this parameter is given below: 
-- SCIBillingChargingCharacteristics				::= CHOICE {
-- 	chargeLevel				[0] OCTET STRING (SIZE (min..max),
-- 	chargePulses			[1] Integer4,
-- 	chargeMessages			[2] OCTET STRING (SIZE (min..max)
--	}
ServiceInteractionIndicators {PARAMETERS-BOUND : bound} ::= OCTET STRING (SIZE (
							bound.&minServiceInteractionIndicatorsLength..
							bound.&maxServiceInteractionIndicatorsLength))
-- Indicators which are exchanged between SSP and SCP to resolve interactions between 
-- IN based services and network based services, respectively between different IN based services.
-- Its content is network signalling/operator specific.
-- The internal structure of this parameter can be defined using ASN.1 and the related Basic
-- Encoding Rules (BER). In such a case the value of this paramter (after the first tag and length
-- information) is the BER encoding of the defined ASN.1 internal structure.
-- The tag of this parameter as defined by ETSI is never replaced.
-- Note this parameter is kept in CS2 for backward compatibility to CS1R, for CS2 see new
-- parameter ServiceInteractionIndicatorsTwo
ServiceInteractionIndicatorsTwo 						::= SEQUENCE {
	forwardServiceInteractionInd		[0] ForwardServiceInteractionInd		OPTIONAL,
	-- applicable to operations IDP, CON, ICA, CWA.
	backwardServiceInteractionInd		[1] BackwardServiceInteractionInd		OPTIONAL,
	-- applicable to operations IDP, CON, CTR, CWA, ETC.
	bothwayThroughConnectionInd			[2] BothwayThroughConnectionInd			OPTIONAL,
	-- applicable to operations CTR, ETC.
	suspendTimer						[3] SuspendTimer						OPTIONAL,
	-- applicable to operations CON, ICA, CWA.
	connectedNumberTreatmentInd			[4] ConnectedNumberTreatmentInd			OPTIONAL,
	-- applicable to operations CON, CTR, CWA, ETC.
	suppressCallDiversionNotification	[5] BOOLEAN 							OPTIONAL,
	-- applicable to CON, ICA, CWA
	suppressCallTransferNotification	[6] BOOLEAN 							OPTIONAL,
	-- applicable to CON, ICA, CWA
	allowCdINNoPresentationInd			[7] BOOLEAN								OPTIONAL,
	-- applicable to CON, ICA, CWA
	-- indicates whether the Number Presentation not allowed indicator of the ISUP
	-- "called IN number" shall be set to presentation allowed (TRUE) or 
	-- presentation not allowed (FALSE)
	userDialogueDurationInd				[8] BOOLEAN								DEFAULT TRUE,
	-- applicable when interaction with the user is required, if the interaction
	-- TRUE means the user interaction may last longer than 90 seconds. Otherwise the 
	-- indicator should be set to FALSE.
	-- used for delaying ISUP T9 timer.
	...
	}
-- Indicators which are exchanged between SSP and SCP to resolve interactions between IN based services
-- and network based services, respectively between different IN based services.

ServiceKey 												::= Integer4
-- Information that allows the SCF to choose the appropriate service logic.
SFBillingChargingCharacteristics {PARAMETERS-BOUND : bound} ::= OCTET STRING (SIZE (
							bound.&minSFBillingChargingLength..
							bound.&maxSFBillingChargingLength))
-- This parameter indicates the billing and/or charging characteristics for filtered calls.
-- Its content is network operator specific.
-- The internal structure of this parameter can be defined using ASN.1 and the related Basic
-- Encoding Rules (BER). In such a case the value of this paramter (after the first tag and length
-- information) is the BER encoding of the defined ASN.1 internal structure.
-- The tag of this parameter as defined by ETSI is never replaced.
SubscriberId {PARAMETERS-BOUND : bound} 					::= GenericNumber {bound}
SupplementaryServices 									::= BIT STRING {
	callingLineIdentificationPresentation 		(1),
	callingLineIdentificationRestriction 		(2),
	connectedLineIdentificationPresentation 	(3),
	connectedLineIdentificationRestriction 		(4),
	callForwardingOnNoReply 					(5),
	callForwardingUnconditional 				(6),
	callForwardingOnBusy 						(7),
	callForwardingOnNotReachable 				(8),
	callWaiting 								(9),
	callHold 									(10),
	reverseCharging 							(11),
	explicitCallTransfer 						(12),
	callCompletionOnBusySubscriber 				(13),
	adviceOfChargeOnStart 						(14),
	adviceOfChargeAtEnd 						(15),
	adviceOfChargeDuringCall 					(16),
	timeDependentRouting 						(17),
	callingPartingDependentRouting 				(18),
	outgoingCallBarring 						(19),
	incomingCallBarring 						(20)
	}
SuspendTimer 											::= INTEGER (-1..120) --value in seconds
-- The default is as specified in EN 301 070-1
-- The value -1 indicates the network specific suspend timer (T6) is to be used.
TerminalType 											::= ENUMERATED {
	unknown										(0),
	dialPulse									(1),
	dtmf										(2),
	isdn										(3),
	isdnNoDtmf									(4),
	spare										(16)
	}
-- Identifies the terminal type so that the SCF can specify, to the SRF, 
-- the appropriate type of capability 
-- (voice recognition, DTMF, display capability, etc.).
TimerID 												::= ENUMERATED {
	tssf										(0)
	-- others for further study
	}
-- Indicates the timer to be reset.
TimerValue 												::= Integer4
-- Indicates the timer value (in seconds).
Tone 													::= SEQUENCE {
	toneID				[0] Integer4,
	duration			[1] Integer4									OPTIONAL,
...
	}
-- The duration specifies the length of the tone in seconds, value 0 indicates infinite duration.
ToneId 													::= CHOICE {
	local				[0] Integer4,
	global				[1] OBJECT IDENTIFIER
	}
TraceInformation {PARAMETERS-BOUND : bound} 				::= SEQUENCE OF TraceItem {bound}
TraceItem {PARAMETERS-BOUND : bound} 					::= SET {scf [0] ScfID {bound},...}
TriggerDataIdentifier {PARAMETERS-BOUND : bound} 		::= SEQUENCE {
	triggerID			[0] EventTypeBCSM,
	profileIdentifier	[1] ProfileIdentifier {bound},
...
	}
-- It is for further study whether al TDP types really apply

UnavailableNetworkResource 								::= ENUMERATED {
	unavailableResources			(0),
	componentFailure				(1),
	basicCallProcessingException	(2),
	resourceStatusFailure			(3),
	endUserFailure					(4)
	}
-- Indicates the network resource that failed.
UserCredit {PARAMETERS-BOUND : bound} 					::= Credit {bound}
UserInteractionModes 									::= BIT STRING {
	voiceMessage 					(0),
	tone 							(1),
	display 						(2)
	}
USIInformation {PARAMETERS-BOUND : bound} 				::= OCTET STRING (SIZE (
			bound.&minUSIInformationLength..bound.&maxUSIInformationLength))
-- Indicates the length of the USIInformation element, maxUSIInformationlength will depend on 
-- the constraints imposed by the network signalling used to transport the USI information.
-- Its content is network signalling/operator specific.
-- The internal structure of this parameter can be defined using ASN.1 and the related Basic
-- Encoding Rules (BER). In such a case the value of this paramter (after the first tag and length
-- information) is the BER encoding of the defined ASN.1 internal structure.
-- The tag of this parameter as defined by ETSI is never replaced.
USIMonitorMode 											::= ENUMERATED {
	monitoringActive				(0),
	monitoringInactive				(1)
	}

-- Indicates if the monitoring relationship for the specified UTSI IE should be 
-- activated or deactivated.

USIServiceIndicator {PARAMETERS-BOUND : bound} 			::= CHOICE{
	global	OBJECT IDENTIFIER,
	local	OCTET STRING (SIZE (
			bound.&minUSIServiceIndicatorLength..
			bound.&maxUSIServiceIndicatorLength))
-- Its content is network signalling/operator specific.
-- The internal structure of this parameter can be defined using ASN.1 and the related Basic
-- Encoding Rules (BER). In such a case the value of this paramter (after the first tag and length
-- information) is the BER encoding of the defined ASN.1 internal structure.
-- The tag of this parameter as defined by ETSI is never replaced.
			}


VariablePart {PARAMETERS-BOUND : bound} 					::= CHOICE {
	integer				[0] Integer4,
	number				[1] Digits {bound},	-- Generic digits
	time				[2] OCTET STRING (SIZE(2)),	-- HH: MM, BCD coded
	date				[3] OCTET STRING (SIZE(3)),	-- YYMMDD, BCD coded
	price				[4] OCTET STRING (SIZE(4))
	}
-- Indicates the variable part of the message.
-- BCD coded variable parts are encoded as described in the examples below.
-- For example, time = 12: 15 would be encoded as: 
--	Bits					HGFE 		DCBA
-- 	leading octet			2			1
--							5			1
-- date = 1993 September 30th would be encoded as: 
--	Bits					HGFE		DCBA
--	leading octet 			3			9
--							9			0
--							0			3 

-- The Definition of range of constants Follows
highLayerCompatibilityLength	INTEGER ::= 2
minCauseLength					INTEGER ::= 2
numOfCounters					INTEGER ::= 100
numOfInfoItems					INTEGER ::= 5
maxCreditUnit 					INTEGER ::= 65536
END

IN-CS2-errortypes {ccitt(0) identified-organization(4) etsi(0) inDomain(1) in-network(1) CS2(20) modules(0) in-cs2-errortypes (1) version1(0)}
-- This module contains the type definitions for the IN CS2 errors.
-- Where a parameter of type CHOICE is tagged with a specific tag value, the tag is automatically 
-- replaced with an EXPLICIT tag of the same value.

DEFINITIONS IMPLICIT TAGS ::=
BEGIN
IMPORTS
ros-InformationObjects, datatypes, errorcodes FROM IN-CS2-object-identifiers	
		{ccitt(0) identified-organization(4) etsi(0) inDomain(1) in-network(1) CS2(20) module(0) in-cs2-object-identifiers(17) version1(0)}
	ERROR
FROM Remote-Operations-Information-Objects ros-InformationObjects 
	InvokeID,
	UnavailableNetworkResource
FROM IN-CS2-datatypes datatypes
	errcode-canceled,
	errcode-cancelFailed,
	errcode-chainingRefused,
	errcode-eTCFailed,
	errcode-improperCallerResponse,
	errcode-missingCustomerRecord,
	errcode-missingParameter,
	errcode-parameterOutOfRange, 
	errcode-requestedInfoError,
	errcode-systemFailure,
	errcode-taskRefused,
	errcode-unavailableResource,
	errcode-unexpectedComponentSequence,
	errcode-unexpectedDataValue,
	errcode-unexpectedParameter,
	errcode-unknownLegID,
	errcode-unknownResource
FROM IN-CS2-errorcodes errorcodes;

-- TYPE DEFINITION FOR IN CS2 ERRORS FOLLOWS

canceled ERROR 				::= {
	CODE	errcode-canceled
	}
-- The operation has been canceled.

cancelFailed ERROR 			::= {
	PARAMETER 	SEQUENCE {
		problem					[0] ENUMERATED {
			unknownOperation		(0),
			tooLate					(1),
			operationNotCancellable	(2)
			},
		operation				[1] InvokeID,
		...
		}
	CODE	errcode-cancelFailed
	}
-- The operation failed to be canceled.

chainingRefused ERROR 		::= {
	CODE	errcode-chainingRefused
	}

eTCFailed ERROR 			::= {
	CODE 	errcode-eTCFailed
	}
-- The establish temporary connection failed.

improperCallerResponse ERROR ::= {
	CODE 	errcode-improperCallerResponse
	}
-- The caller response was not as expected.

missingCustomerRecord ERROR ::= {
	CODE 	errcode-missingCustomerRecord
	}
-- The Service Logic Program could not be found in the SCF.

missingParameter ERROR 		::= {
	CODE 	errcode-missingParameter
	}
-- An expected optional parameter was not received.

parameterOutOfRange ERROR 	::= {
	CODE 	errcode-parameterOutOfRange
	}
-- The parameter was not as expected (e.g. missing or out of range).

requestedInfoError ERROR 	::= {
	PARAMETER	 ENUMERATED {
			unknownRequestedInfo		(1),
			requestedInfoNotAvailable	(2)
			-- other values FOR FURTHER STUDY
			}
	CODE 	errcode-requestedInfoError
	}
-- The requested information cannot be found.

systemFailure ERROR 		::= {
	PARAMETER	UnavailableNetworkResource
	CODE 	errcode-systemFailure
	}
-- The operation could not be completed due to a system failure at the serving physical entity.

taskRefused ERROR 			::= {
	PARAMETER	ENUMERATED {
			generic						(0),
			unobtainable 				(1),
			congestion					(2)
			--other values FOR FURTHER STUDY
			}
	CODE 	errcode-taskRefused
	}
-- An entity normally capable of the task requested cannot or chooses not to perform the task at 
-- this time. This includes error situations like congestion and unobtainable address as used in 
-- e.g. the connect operation.)

unavailableResource ERROR 	::= {
	CODE 	errcode-unavailableResource
	}
-- A requested resource is not available at the serving entity.

unexpectedComponentSequence ERROR ::= {
	CODE 	errcode-unexpectedComponentSequence
	}
-- An incorrect sequence of Components was received (e.g. "DisconnectForwardConnection" 
-- followed by "PlayAnnouncement").

unexpectedDataValue ERROR ::= {
	CODE 	errcode-unexpectedDataValue
	}
-- The data value was not as expected (e.g. routing number expected but billing number received)

unexpectedParameter ERROR ::= {
	CODE 	errcode-unexpectedParameter
	}
-- A parameter received was not expected.

unknownLegID ERROR 		::= {
	CODE 	errcode-unknownLegID
	}
-- Leg not known to the SSF.

unknownResource ERROR 	::= {
	CODE 	errcode-unknownResource
	}
-- Resource whose status is being requested is not known to the serving entity.

END

IN-CS2-operationcodes {ccitt(0) identified-organization(4) etsi(0) inDomain(1) in-network(1) CS2(20) modules(0) in-cs2-operationcodes (2) version1(0)}
DEFINITIONS ::=
BEGIN

IMPORTS
ros-InformationObjects FROM IN-CS2-object-identifiers	
		{ccitt(0) identified-organization(4) etsi(0) inDomain(1) in-network(1) CS2(20) modules(0) in-cs2-object-identifiers(17) version1(0)}
	Code
FROM Remote-Operations-Information-Objects ros-InformationObjects 
;

-- the operations are grouped by the identified operation packages.

-- SCF activation Package
	opcode-initialDP							Code ::= local: 0
-- SCF/SRF activation of assist Package
	opcode-assistRequestInstructions			Code ::= local: 16
-- Assist connection establishment Package
	opcode-establishTemporaryConnection			Code ::= local: 17
-- Generic disconnect resource Package
	opcode-disconnectForwardConnection			Code ::= local: 18
	opcode-dFCWithArgument						Code ::= local: 86
-- Non-assisted connection establishment Package

	opcode-connectToResource					Code ::= local: 19
-- Connect Package (elementary SSF function)
	opcode-connect								Code ::= local: 20
-- Call handling Package (elementary SSF function)
	opcode-releaseCall							Code ::= local: 22
-- BCSM Event handling Package
	opcode-requestReportBCSMEvent				Code ::= local: 23
	opcode-eventReportBCSM						Code ::= local: 24
-- Charging Event handling Package
	opcode-requestNotificationChargingEvent		Code ::= local: 25
	opcode-eventNotificationCharging			Code ::= local: 26
-- SSF call processing Package
	opcode-collectInformation					Code ::= local: 27
	opcode-continue								Code ::= local: 31
-- SCF call initiation Package
	opcode-initiateCallAttempt					Code ::= local: 32
-- Timer Package
	opcode-resetTimer							Code ::= local: 33
-- Billing Package
	opcode-furnishChargingInformation			Code ::= local: 34
-- Charging Package
	opcode-applyCharging						Code ::= local: 35
	opcode-applyChargingReport					Code ::= local: 36
-- Traffic management Package
	opcode-callGap								Code ::= local: 41
-- Service management Package
	opcode-activateServiceFiltering				Code ::= local: 42
	opcode-serviceFilteringResponse				Code ::= local: 43
-- Call report Package
	opcode-callInformationReport				Code ::= local: 44
	opcode-callInformationRequest				Code ::= local: 45
-- Signalling control Package
	opcode-sendChargingInformation				Code ::= local: 46
-- Specialized resource control Package
	opcode-playAnnouncement						Code ::= local: 47
	opcode-promptAndCollectUserInformation		Code ::= local: 48
	opcode-specializedResourceReport			Code ::= local: 49
-- Cancel Package
	opcode-cancel								Code ::= local: 53
-- Activity Test Package
	opcode-activityTest							Code ::= local: 55
-- CPH Response Package
	opcode-continueWithArgument					Code ::= local: 88
	opcode-createCallSegmentAssociation			Code ::= local: 89
	opcode-disconnectLeg						Code ::= local: 90
	opcode-mergeCallSegments					Code ::= local: 91
	opcode-moveCallSegments						Code ::= local: 92
	opcode-moveLeg								Code ::= local: 93 
	opcode-splitLeg								Code ::= local: 95
-- Exception Inform Package
	opcode-entityReleased						Code ::= local: 96
-- Trigger Management Package
	opcode-manageTriggerData					Code ::= local: 97
-- USI Handling Package
	opcode-requestReportUTSI					Code ::= local: 98
	opcode-sendSTUI								Code ::= local: 100
	opcode-reportUTSI							Code ::= local: 101

-- SRF/SCF interface
	opcode-promptAndReceiveMessage				Code ::= local: 107
	opcode-scriptInformation					Code ::= local: 108
	opcode-scriptEvent							Code ::= local: 109
	opcode-scriptRun							Code ::= local: 110
	opcode-scriptClose							Code ::= local: 111

-- SCF/SCF interface
	opcode-establishChargingRecord				Code ::= local: 112
	opcode-handlingInformationRequest			Code ::= local: 113
	opcode-handlingInformationResult			Code ::= local: 114
	opcode-networkCapability					Code ::= local: 115
	opcode-notificationProvided					Code ::= local: 116
	opcode-confirmedNotificationProvided		Code ::= local: 117
	opcode-provideUserInformation				Code ::= local: 118
	opcode-confirmedReportChargingInformation	Code ::= local: 119
	opcode-reportChargingInformation			Code ::= local: 120
	opcode-requestNotification					Code ::= local: 121

-- CUSF/SCF interface
	opcode-initiateAssociation					Code ::= local: 123
	opcode-releaseAssociation					Code ::= local: 126
	opcode-requestReportBCUSMEvent				Code ::= local: 127
 	opcode-initialAssociationDP					Code ::= local: 131
	opcode-connectAssociation					Code ::= local: 132
	opcode-continueAssociation					Code ::= local: 133
	opcode-eventReportBCUSM						Code ::= local: 134

END

IN-CS2-errorcodes {ccitt(0) identified-organization(4) etsi(0) inDomain(1) in-network(1) CS2(20) modules(0) in-cs2-errorcodes (3) version1(0)}
DEFINITIONS ::=
BEGIN
IMPORTS
ros-InformationObjects FROM IN-CS2-object-identifiers	
		{ccitt(0) identified-organization(4) etsi(0) inDomain(1) in-network(1) CS2(20) modules(0) in-cs2-object-identifiers(17) version1(0)}
	Code
FROM Remote-Operations-Information-Objects ros-InformationObjects 
;
	errcode-canceled							Code ::= local: 0
	errcode-cancelFailed						Code ::= local: 1
	errcode-eTCFailed							Code ::= local: 3
	errcode-improperCallerResponse				Code ::= local: 4
	errcode-missingCustomerRecord				Code ::= local: 6
	errcode-missingParameter					Code ::= local: 7
	errcode-parameterOutOfRange					Code ::= local: 8
	errcode-requestedInfoError					Code ::= local: 10
	errcode-systemFailure						Code ::= local: 11
	errcode-taskRefused							Code ::= local: 12
	errcode-unavailableResource					Code ::= local: 13
	errcode-unexpectedComponentSequence			Code ::= local: 14
	errcode-unexpectedDataValue					Code ::= local: 15
	errcode-unexpectedParameter					Code ::= local: 16
	errcode-unknownLegID						Code ::= local: 17
	errcode-unknownResource						Code ::= local: 18

-- Error codes for the new IN CS2 error types 
	errcode-scfReferral							Code ::= local: 21
	errcode-scfTaskRefused						Code ::= local: 22
	errcode-chainingRefused						Code ::= local: 23

END

IN-CS2-classes {ccitt(0) identified-organization(4) etsi(0) inDomain(1) in-network(1) CS2(20) modules(0) in-cs2-classes (4) version1(0)}
DEFINITIONS ::=
BEGIN

IMPORTS

	ROS-OBJECT-CLASS, CONTRACT, OPERATION-PACKAGE, Code, OPERATION, 
	CONNECTION-PACKAGE
FROM Remote-Operations-Information-Objects ros-InformationObjects

	emptyBind, emptyUnbind
FROM Remote-Operations-Useful-Definitions ros-UsefulDefinitions

	id-package-emptyConnection,
	id-rosObject-scf,
	id-rosObject-cusf,
	id-rosObject-dssp,
	id-rosObject-srf,
	id-rosObject-ssf,
	ros-InformationObjects,
	ros-UsefulDefinitions,
	ssf-scf-Protocol,
	scf-cusf-Protocol,
	scf-scf-Protocol,
	scf-srf-Protocol,
	scf-sdf-Protocol,
	datatypes
FROM IN-CS2-object-identifiers {ccitt(0) identified-organization(4) etsi(0) inDomain(1) in-network(1) CS2(20) modules(0) in-cs2-object-identifiers (17) version1(0)}

	inCs2AssistHandoffssfToScf, 
	inCs2ScfToSsfGeneric, 
	inCs2ScfToSsfTrafficManagement, 
	inCs2SsfToScfGeneric, 
	inCs2SsfToScfServiceManagement
FROM IN-CS2-SSF-SCF-pkgs-contracts-acs ssf-scf-Protocol

	cusf-scf-contract,
	scf-cusf-contract
FROM IN-CS2-SCF-CUSF-pkgs-contracts-acs scf-cusf-Protocol 

	dsspContract,
	scf-scfContract
FROM IN-CS2-SCF-SCF-pkgs-contracts-acs scf-scf-Protocol 

	srf-scf-contract
FROM IN-CS2-SCF-SRF-pkgs-contracts-acs scf-srf-Protocol

	dapContract
	FROM IN-CS2-SCF-SDF-Protocol scf-sdf-Protocol
	CriticalityType
FROM IN-CS2-datatypes datatypes
;

ssf ROS-OBJECT-CLASS ::= {
	INITIATES	{inCs2SsfToScfGeneric|
				inCs2AssistHandoffssfToScf|
				inCs2SsfToScfServiceManagement}
	RESPONDS	{inCs2ScfToSsfGeneric|
				inCs2ScfToSsfTrafficManagement|
				inCs2SsfToScfServiceManagement|
	ID			id-rosObject-ssf}

srf ROS-OBJECT-CLASS ::= {
	INITIATES	{srf-scf-contract} 
	ID			id-rosObject-srf
	}
cusf ROS-OBJECT-CLASS ::= {
	INITIATES	{cusf-scf-contract} 
	RESPONDS	{scf-cusf-contract} 
	ID			id-rosObject-cusf}
dssp ROS-OBJECT-CLASS ::= {
	BOTH		{dsspContract}
	ID			id-rosObject-dssp
	}

scf ROS-OBJECT-CLASS ::= {
	INITIATES	{inCs2ScfToSsfGeneric|
				inCs2ScfToSsfTrafficManagement|
				inCs2ScfToSsfServiceManagement|
				inCs2ScfToSsfTriggerManagement|
-- scf to cusf contracts
				scf-cusf-contract | 
-- scf to scf contracts
				scf-scfContract |
				dsspContract |
-- sdf to scf contracts
				dapContract
				}
	RESPONDS	{inCs2SsfToScfGeneric|
				inCs2AssistHandoffssfToScf|
				inCs2SsfToScfServiceManagement|
-- cusf to scf contracts
				cusf-scf-contract | 
-- srf to scf contracts
				srf-scf-contract |
-- scf to scf contracts
				scf-scfContract |
				dsspContract 

				}
	ID			id-rosObject-scf}

EXTENSION ::= CLASS {
	&ExtensionType,
	&criticality	CriticalityType DEFAULT ignore,
	&id	Code
	}
WITH SYNTAX {
	EXTENSION-SYNTAX	&ExtensionType
	CRITICALITY			&criticality
	IDENTIFIED BY		&id
	}

-- Example of addition of an extension named 'Some Network Specific Indicator' of type
-- BOOLEAN, with criticality 'abort' and to be identified as extension number 1
-- Example of definition using the above information object class: 
--
-- SomeNetworkSpecificIndicator EXTENSION ::= {
-- 	EXTENSION-SYNTAX	BOOLEAN
--	CRITICALITY			abort
--	IDENTIFIED BY		local: 1
--	}

-- Example of transfer syntax, using the ExtensionField datatype as specified in subclause 4.1.
-- Assuming the value of the extension is set to TRUE, the extensions parameter
-- becomes a Sequence of type INTEGER ::= 1, criticality ENUMERATED ::= 1 and value [1]
-- EXPLICIT BOOLEAN ::= TRUE.
--
-- Use of Q.1400 defined Extension is for further study.
-- In addition the extension mechanism marker is used to identify the future minor additions
-- to INAP.
firstExtension EXTENSION ::= {
	EXTENSION-SYNTAX	NULL
	CRITICALITY			ignore
	IDENTIFIED BY		local: 1
	}
-- firstExtension is just an example.
SupportedExtensions {PARAMETERS-BOUND : bound} EXTENSION ::= {firstExtension, ...
-- full set of network operator extensions -
}
-- SupportedExtension is the full set of the network operator extensions.
UISCRIPT ::= CLASS {
	&SpecificInfo	OPTIONAL,
	&Result			OPTIONAL,
	&id	Code
	}
WITH SYNTAX {
	[WITH-SPECIFICINFO 	&SpecificInfo]
	[WITH-RESULT 		&Result]
	IDENTIFIED BY	 	&id
}

firstScript UISCRIPT ::=
	{
	IDENTIFIED BY local: 1
	}
-- firstScript is just an example.
SupportedUIScripts {PARAMETERS-BOUND : bound} UISCRIPT ::= {firstScript, ...
-- full set of User Interaction script -
} 
-- SupportedUIScripts is the full set of User Interaction scripts.

inEmptyUnbind OPERATION ::= {
	RETURN RESULT	FALSE
	ALWAYS RESPONDS	FALSE}
emptyConnectionPackage CONNECTION-PACKAGE ::= {
	BIND	emptyBind
	UNBIND	inEmptyUnbind
	RESPONDER UNBIND 	TRUE
	ID		id-package-emptyConnection
	}
PARAMETERS-BOUND ::= CLASS
{
	&minAChBillingChargingLength				INTEGER,
	&maxAChBillingChargingLength				INTEGER,
	&minAssReleaseInfoLength					INTEGER,
	&maxAssReleaseInfoLength					INTEGER,
	&minAttributesLength						INTEGER,
	&maxAttributesLength						INTEGER,
	&minBackwardGVNSLength						INTEGER,
	&maxBackwardGVNSLength						INTEGER,
	&maxBearerCapabilityLength					INTEGER,
	&minCalledPartyBCDNumberLength				INTEGER,
	&maxCalledPartyBCDNumberLength				INTEGER,
	&minCalledPartyNumberLength					INTEGER,
	&maxCalledPartyNumberLength					INTEGER,
	&minCallingPartyBusinessGroupIDLength		INTEGER,
	&maxCallingPartyBusinessGroupIDLength		INTEGER,
	&minCallingPartyNumberLength				INTEGER,
	&maxCallingPartyNumberLength				INTEGER,
	&minCallingPartySubAddressLength			INTEGER,
	&maxCallingPartySubAddressLength			INTEGER,
	&minCallResultLength						INTEGER,
	&maxCallResultLength						INTEGER,
	&minCarrierLength							INTEGER,
	&maxCarrierLength							INTEGER,
	&maxCauseLength								INTEGER,
	&minCompReceivedInfoLength					INTEGER,
	&maxCompReceivedInfoLength					INTEGER,
	&minDigitsLength							INTEGER,
	&maxDigitsLength							INTEGER,
	&minDisplayInformationLength				INTEGER,
	&maxDisplayInformationLength				INTEGER,
	&minEventSpecificInformationChargingLength	INTEGER,
	&maxEventSpecificInformationChargingLength	INTEGER,
	&minEventTypeChargingLength					INTEGER,
	&maxEventTypeChargingLength					INTEGER,
	&minFCIbccCS1Length							INTEGER,
	&maxFCIbccCS1Length							INTEGER,
	&minFCIbccCS2Length							INTEGER,
	&maxFCIbccCS2Length							INTEGER,
	&minForwardGVNSLength						INTEGER,
	&maxForwardGVNSLength						INTEGER,
	&minGenericNameLength						INTEGER,
	&maxGenericNameLength						INTEGER,
	&minGenericNumberLength						INTEGER,
	&maxGenericNumberLength						INTEGER,
	&maxInitialTimeInterval						INTEGER,
	&maxINServiceCompatibilityIndLength			INTEGER,
	&minIPAvailableLength						INTEGER,
	&maxIPAvailableLength						INTEGER,
	&minIPSSPCapabilitiesLength					INTEGER,
	&maxIPSSPCapabilitiesLength					INTEGER,
	&minISDNAccessRelatedInformationLength		INTEGER,
	&maxISDNAccessRelatedInformationLength		INTEGER,
	&minLocationNumberLength					INTEGER,
	&maxLocationNumberLength					INTEGER,
	&minMailBoxIDLength							INTEGER,
	&maxMailBoxIDLength							INTEGER,
	&minMessageContentLength					INTEGER,
	&maxMessageContentLength					INTEGER,
	&minMidCallControlInfoNum					INTEGER,
	&maxMidCallControlInfoNum					INTEGER,
	&minOriginalCalledPartyIDLength				INTEGER,
	&maxOriginalCalledPartyIDLength				INTEGER,
	&minReasonLength							INTEGER,
	&maxReasonLength							INTEGER,
	&minReceivedInformationLength				INTEGER,
	&maxReceivedInformationLength 				INTEGER,
	&maxRecordedMessageUnits					INTEGER,
	&maxRecordingTime							INTEGER,
	&minRedirectingPartyIDLength				INTEGER,
	&maxRedirectingPartyIDLength				INTEGER,
	&minRegistratorIdentifierLength				INTEGER,
	&maxRegistratorIdentifierLength				INTEGER,
	&minRequestedUTSINum 						INTEGER,
	&maxRequestedUTSINum 						INTEGER,
	&minRouteListLength							INTEGER,
	&maxRouteListLength							INTEGER,
	&minScfIDLength								INTEGER,
	&maxScfIDLength								INTEGER,
	&minScfAddressLength						INTEGER,
	&maxScfAddressLength						INTEGER,
	&minSCIBillingChargingLength				INTEGER,
	&maxSCIBillingChargingLength				INTEGER,
	&minServiceInteractionIndicatorsLength		INTEGER,
	&maxServiceInteractionIndicatorsLength		INTEGER,
	&minSFBillingChargingLength					INTEGER,
	&maxSFBillingChargingLength					INTEGER,
	&minUSIInformationLength					INTEGER,
	&maxUSIInformationLength					INTEGER,
	&minUSIServiceIndicatorLength				INTEGER,
	&maxUSIServiceIndicatorLength				INTEGER,
	&numOfBCSMEvents							INTEGER,
	&numOfBCUSMEvents							INTEGER,
	&numOfChargingEvents						INTEGER,
	&numOfCSAs									INTEGER,
	&numOfCSs									INTEGER,
	&numOfExtensions							INTEGER,
	&numOfGenericNumbers						INTEGER,
	&numOfInServiceCompatibilityIndLength		INTEGER,
	&numOfLegs									INTEGER,
	&numOfMessageIDs							INTEGER,
	&maxAmount									INTEGER,
	&maxInitialUnitIncrement					INTEGER,
	&maxScalingFactor							INTEGER,
	&maxSegmentsPerDataInterval					INTEGER,
	&maxTimePerInterval							INTEGER,
	&maxUnitsPerDataInterval 					INTEGER,
	&maxUnitsPerInterval						INTEGER,
	&ub-maxUserCredit							INTEGER,
	&ub-nbCall									INTEGER
}
WITH SYNTAX
{
	MINIMUM-FOR-ACH-BILLING-CHARGING			&minAChBillingChargingLength
	MAXIMUM-FOR-ACH-BILLING-CHARGING			&maxAChBillingChargingLength
	MINIMUM-FOR-ASSOCIATION-RELEASE-INFO		&minAssReleaseInfoLength
	MAXIMUM-FOR-ASSOCIATION-RELEASE-INFO		&maxAssReleaseInfoLength
	MINIMUM-FOR-ATTRIBUTES						&minAttributesLength
	MAXIMUM-FOR-ATTRIBUTES						&maxAttributesLength
	MAXIMUM-FOR-BACKWARD-GVNS					&minBackwardGVNSLength
	MAXIMUM-FOR-BACKWARD-GVNS					&maxBackwardGVNSLength
	MAXIMUM-FOR-BEARER-CAPABILITY				&maxBearerCapabilityLength
	MINIMUM-FOR-CALLED-PARTY-BCD-NUMBER			&minCalledPartyBCDNumberLength
	MAXIMUM-FOR-CALLED-PARTY-BCD-NUMBER			&maxCalledPartyBCDNumberLength
	MINIMUM-FOR-CALLED-PARTY-NUMBER				&minCalledPartyNumberLength
	MAXIMUM-FOR-CALLED-PARTY-NUMBER				&maxCalledPartyNumberLength
	MINIMUM-FOR-CALLING-PARTY-BUSINESS-GROUP-ID	&minCallingPartyBusinessGroupIDLength
	MAXIMUM-FOR-CALLING-PARTY-BUSINESS-GROUP-ID	&maxCallingPartyBusinessGroupIDLength
	MINIMUM-FOR-CALLING-PARTY-NUMBER			&minCallingPartyNumberLength
	MAXIMUM-FOR-CALLING-PARTY-NUMBER			&maxCallingPartyNumberLength
	MINIMUM-FOR-CALLING-PARTY-SUBADDRESS		&minCallingPartySubAddressLength
	MAXIMUM-FOR-CALLING-PARTY-SUBADDRESS		&maxCallingPartySubAddressLength
	MINIMUM-FOR-CALL-RESULT						&minCallResultLength
	MAXIMUM-FOR-CALL-RESULT						&maxCallResultLength
	MINIMUM-FOR-CARRIER							&minCarrierLength
	MAXIMUM-FOR-CARRIER							&maxCarrierLength
	MAXIMUM-FOR-CAUSE							&maxCauseLength
	MINIMUM-FOR-COMPONENT-RECEIVED-INFO			&minCompReceivedInfoLength
	MAXIMUM-FOR-COMPONENT-RECEIVED-INFO			&maxCompReceivedInfoLength
	MINIMUM-FOR-DIGITS							&minDigitsLength
	MAXIMUM-FOR-DIGITS							&maxDigitsLength
	MINIMUM-FOR-DISPLAY							&minDisplayInformationLength
	MAXIMUM-FOR-DISPLAY							&maxDisplayInformationLength
	MINIMUM-FOR-EVENT-SPECIFIC-CHARGING			&minEventSpecificInformationChargingLength
	MAXIMUM-FOR-EVENT-SPECIFIC-CHARGING			&maxEventSpecificInformationChargingLength
	MINIMUM-FOR-EVENT-TYPE-CHARGING				&minEventTypeChargingLength
	MAXIMUM-FOR-EVENT-TYPE-CHARGING				&maxEventTypeChargingLength
	MINIMUM-FOR-FCI-BILLING-CHARGING-CS1		&minFCIbccCS1Length
	MAXIMUM-FOR-FCI-BILLING-CHARGING-CS1		&maxFCIbccCS1Length
	MINIMUM-FOR-FCI-BILLING-CHARGING-CS2		&minFCIbccCS2Length
	MAXIMUM-FOR-FCI-BILLING-CHARGING-CS2		&maxFCIbccCS2Length
	MINIMUM-FOR-FORWARD-GVNS					&minForwardGVNSLength
	MAXIMUM-FOR-FORWARD-GVNS					&maxForwardGVNSLength
	MINIMUM-FOR-GENERIC-NAME					&minGenericNameLength
	MAXIMUM-FOR-GENERIC-NAME					&maxGenericNameLength
	MINIMUM-FOR-GENERIC-NUMBER					&minGenericNumberLength
	MAXIMUM-FOR-GENERIC-NUMBER					&maxGenericNumberLength
	MAXIMUM-FOR-INITIAL-TIME-INTERVAL			&maxInitialTimeInterval
	MAXIMUM-FOR-IN-SERVICE-COMPATIBILITY		&maxINServiceCompatibilityIndLength
	MINIMUM-FOR-IP-AVAILABLE					&minIPAvailableLength
	MAXIMUM-FOR-IP-AVAILABLE					&maxIPAvailableLength
	MINIMUM-FOR-IP-SSP-CAPABILITIES				&minIPSSPCapabilitiesLength
	MAXIMUM-FOR-IP-SSP-CAPABILITIES				&maxIPSSPCapabilitiesLength
	MINIMUM-FOR-ISDN-ACCESS-RELATED-INFO		&minISDNAccessRelatedInformationLength
	MAXIMUM-FOR- ISDN-ACCESS-RELATED-INFO		&maxISDNAccessRelatedInformationLength
	MINIMUM-FOR-LOCATION-NUMBER					&minLocationNumberLength
	MAXIMUM-FOR-LOCATION-NUMBER					&maxLocationNumberLength
	MINIMUM-FOR-MAIL-BOX-ID						&minMailBoxIDLength
	MAXIMUM-FOR-MAIL-BOX-ID						&maxMailBoxIDLength
	MINIMUM-FOR-MESSAGE-CONTENT					&minMessageContentLength
	MAXIMUM-FOR-MESSAGE-CONTENT					&maxMessageContentLength
	MINIMUM-FOR-MID-CALL-CONTROL-INFO			&minMidCallControlInfoNum
	MAXIMUM-FOR-MID-CALL-CONTROL-INFO			&maxMidCallControlInfoNum
	MINIMUM-FOR-ORIGINAL-CALLED-PARTY-ID		&minOriginalCalledPartyIDLength
	MAXIMUM-FOR-ORIGINAL-CALLED-PARTY-ID		&maxOriginalCalledPartyIDLength
	MINIMUM-FOR-REASON							&minReasonLength
	MAXIMUM-FOR-REASON							&maxReasonLength
	MINIMUM-FOR-RECEIVED-INFORMATION			&minReceivedInformationLength
	MAXIMUM-FOR-RECEIVED-INFORMATION			&maxReceivedInformationLength 
	MAXIMUM-FOR-RECORDED-MESSAGE-UNITS			&maxRecordedMessageUnits
	MAXIMUM-FOR-RECORDING-TIME					&maxRecordingTime
	MINIMUM-FOR-REDIRECTING-ID					&minRedirectingPartyIDLength
	MAXIMUM-FOR-REDIRECTING-ID					&maxRedirectingPartyIDLength
	MINIMUM-FOR-REGISTRATOR-IDENTIFIER			&minRegistratorIdentifierLength
	MAXIMUM-FOR- REGISTRATOR-IDENTIFIER			&maxRegistratoridentifierLength
	MINIMUM-FOR-REQUESTED-UTSI-NUM				&minRequestedUTSINum
	MAXIMUM-FOR-REQUESTED-UTSI-NUM				&maxRequestedUTSINum 
	MINIMUM-FOR-ROUTE-LIST						&minRouteListLength
	MAXIMUM-FOR-ROUTE-LIST						&maxRouteListLength
	MINIMUM-FOR-SCF-ID							&minScfIDLength
	MAXIMUM-FOR-SCF-ID							&maxScfIDLength
	MINIMUM-FOR-SCF-ADDRESS						&minScfAddressLength
	MAXIMUM-FOR-SCF-ADDRESS						&maxScfAddressLength
	MINIMUM-FOR-SCI-BILLING-CHARGING			&minSCIBillingChargingLength
	MAXIMUM-FOR-SCI-BILLING-CHARGING			&maxSCIBillingChargingLength
	MINIMUM-FOR-SII								&minServiceInteractionIndicatorsLength
	MAXIMUM-FOR-SII								&maxServiceInteractionIndicatorsLength
	MINIMUM-FOR-SF-BILLING-CHARGING				&minSFBillingChargingLength
	MAXIMUM-FOR-SF-BILLING-CHARGING				&maxSFBillingChargingLength
	MINIMUM-FOR-USI-INFORMATION					&minUSIInformationLength
	MAXIMUM-FOR-USI-INFORMATION					&maxUSIInformationLength
	MINIMUM-FOR-USI-SERVICE-INDICATOR			&minUSIServiceIndicatorLength
	MAXIMUM-FOR-USI-SERVICE-INDICATOR			&maxUSIServiceIndicatorLength
	NUM-OF-BCSM-EVENT							&numOfBCSMEvents
	NUM-OF-BCUSM-EVENT							&numOfBCUSMEvents
	NUM-OF-CHARGING-EVENT						&numOfChargingEvents
	NUM-OF-CSAS									&numOfCSAs
	NUM-OF-CSS									&numOfCSs
	NUM-OF-EXTENSIONS							&numOfExtensions
	NUM-OF-GENERIC-NUMBERS						&numOfGenericNumbers
	NUM-OF-IN-SERVICE-COMPATIBILITY-ID			&numOfInServiceCompatibilityIndLength
	NUM-OF-LEGS									&numOfLegs
	NUM-OF-MESSAGE-IDS							&numOfMessageIDs
	MAXIMUM-FOR-AMOUNT							&maxAmount
	MAXIMUM-FOR-INITIAL-UNIT-INCREMENT			&maxInitialUnitIncrement
	MAXIMUM-FOR-SCALING-FACTOR					&maxScalingFactor
	MAXIMUM-FOR-SEGMENTS-PER-DATA-INTERVAL		&maxSegmentsPerDataInterval
	MAXIMUM-FOR-TIME-PER-INTERVAL				&maxTimePerInterval
	MAXIMUM-FOR-UNITS-PER-DATA-INTERVAL			&maxUnitsPerDataInterval 
	MAXIMUM-FOR-UNITS-PER-INTERVAL				&maxUnitsPerInterval
	MAXIMUM-FOR-UB-USER-CREDIT					&ub-maxUserCredit
	MAXIMUM-FOR-UB-NB-CALL						&ub-nbCall
}


-- The following instance of the parameter bound is just an example
networkSpecificBoundSet PARAMETERS-BOUND ::=
{
	MINIMUM-FOR-ACH-BILLING-CHARGING			1	-- example value
	MAXIMUM-FOR-ACH-BILLING-CHARGING			5	-- example value
	MINIMUM-FOR-ASSOCIATION-RELEASE-INFO		1	-- example value
	MAXIMUM-FOR-ASSOCIATION-RELEASE-INFO		5	-- example value
	MINIMUM-FOR-ATTRIBUTES						1	-- example value
	MAXIMUM-FOR-ATTRIBUTES						5	-- example value
	MAXIMUM-FOR-BACKWARD-GVNS					1	-- example value
	MAXIMUM-FOR-BACKWARD-GVNS					5	-- example value
	MAXIMUM-FOR-BEARER-CAPABILITY				5	-- example value
	MINIMUM-FOR-CALLED-PARTY-BCD-NUMBER			1	-- example value
	MAXIMUM-FOR-CALLED-PARTY-BCD-NUMBER			5	-- example value
	MINIMUM-FOR-CALLED-PARTY-NUMBER				1	-- example value
	MAXIMUM-FOR-CALLED-PARTY-NUMBER				5	-- example value
	MINIMUM-FOR-CALLING-PARTY-BUSINESS-GROUP-ID	1	-- example value
	MAXIMUM-FOR-CALLING-PARTY-BUSINESS-GROUP-ID	5	-- example value
	MINIMUM-FOR-CALLING-PARTY-NUMBER			1	-- example value
	MAXIMUM-FOR-CALLING-PARTY-NUMBER			5	-- example value
	MINIMUM-FOR-CALLING-PARTY-SUBADDRESS		1	-- example value
	MAXIMUM-FOR-CALLING-PARTY-SUBADDRESS		5	-- example value
	MINIMUM-FOR-CALL-RESULT						1	-- example value
	MAXIMUM-FOR-CALL-RESULT						5	-- example value
	MINIMUM-FOR-CARRIER							1	-- example value
	MAXIMUM-FOR-CARRIER							5	-- example value
	MAXIMUM-FOR-CAUSE							4	-- example value
	MINIMUM-FOR-DIGITS							1	-- example value
	MAXIMUM-FOR-DIGITS							5	-- example value
	MINIMUM-FOR-DISPLAY							1	-- example value
	MAXIMUM-FOR-DISPLAY							5	-- example value
	MINIMUM-FOR-EVENT-SPECIFIC-CHARGING			1	-- example value
	MAXIMUM-FOR-EVENT-SPECIFIC-CHARGING			5	-- example value
	MINIMUM-FOR-EVENT-TYPE-CHARGING				1	-- example value
	MAXIMUM-FOR-EVENT-TYPE-CHARGING				5	-- example value
	MINIMUM-FOR-FCI-BILLING-CHARGING-CS1		1	-- example value
	MAXIMUM-FOR-FCI-BILLING-CHARGING-CS1		5	-- example value
	MINIMUM-FOR-FCI-BILLING-CHARGING-CS2		1	-- example value
	MAXIMUM-FOR-FCI-BILLING-CHARGING-CS2		5	-- example value
	MINIMUM-FOR-FORWARD-GVNS					1	-- example value
	MAXIMUM-FOR-FORWARD-GVNS					5	-- example value
	MINIMUM-FOR-GENERIC-NAME					1	-- example value
	MAXIMUM-FOR-GENERIC-NAME					5	-- example value
	MINIMUM-FOR-GENERIC-NUMBER					1	-- example value
	MAXIMUM-FOR-GENERIC-NUMBER					5	-- example value
	MAXIMUM-FOR-INITIAL-TIME-INTERVAL			5	-- example value
	MAXIMUM-FOR-IN-SERVICE-COMPATIBILITY		5	-- example value
	MINIMUM-FOR-IP-AVAILABLE					1	-- example value
	MAXIMUM-FOR-IP-AVAILABLE					5	-- example value
	MINIMUM-FOR-IP-SSP-CAPABILITIES				1	-- example value
	MAXIMUM-FOR-IP-SSP-CAPABILITIES				5	-- example value
	MINIMUM-FOR-ISDN-ACCESS-RELATED-INFO		1	-- example value
	MAXIMUM-FOR- ISDN-ACCESS-RELATED-INFO		5	-- example value
	MINIMUM-FOR-LOCATION-NUMBER					1	-- example value
	MAXIMUM-FOR-LOCATION-NUMBER					5	-- example value
	MINIMUM-FOR-MAIL-BOX-ID						1	-- example value
	MAXIMUM-FOR-MAIL-BOX-ID						5	-- example value
	MINIMUM-FOR-MESSAGE-CONTENT					1	-- example value
	MAXIMUM-FOR-MESSAGE-CONTENT					5	-- example value
	MINIMUM-FOR-MID-CALL-CONTROL-INFO			1	-- example value
	MAXIMUM-FOR-MID-CALL-CONTROL-INFO			5	-- example value
	MINIMUM-FOR-ORIGINAL-CALLED-PARTY-ID		1	-- example value
	MAXIMUM-FOR-ORIGINAL-CALLED-PARTY-ID		5	-- example value
	MINIMUM-FOR-REASON							1	-- example value
	MAXIMUM-FOR-REASON							5	-- example value
	MINIMUM-FOR-RECEIVED-INFORMATION			1	-- example value
	MAXIMUM-FOR-RECEIVED-INFORMATION			5	-- example value
	MAXIMUM-FOR-RECORDED-MESSAGE-UNITS			5	-- example value
	MAXIMUM-FOR-RECORDING-TIME					5	-- example value
	MINIMUM-FOR-REDIRECTING-ID					1	-- example value
	MAXIMUM-FOR-REDIRECTING-ID					5	-- example value
	MINIMUM-FOR-REGISTRATOR-IDENTIFIER			1	-- example value
	MAXIMUM-FOR- REGISTRATOR-IDENTIFIER			5	-- example value
	MINIMUM-FOR-REQUESTED-UTSI-NUM				1	-- example value
	MAXIMUM-FOR-REQUESTED-UTSI-NUM				5	-- example value
	MINIMUM-FOR-ROUTE-LIST						1	-- example value
	MAXIMUM-FOR-ROUTE-LIST						5	-- example value
	MINIMUM-FOR-SCF-ID							1	-- example value
	MAXIMUM-FOR-SCF-ID							5	-- example value
	MINIMUM-FOR-SCF-ADDRESS						1	-- example value
	MAXIMUM-FOR-SCF-ADDRESS						5	-- example value
	MINIMUM-FOR-SCI-BILLING-CHARGING			1	-- example value
	MAXIMUM-FOR-SCI-BILLING-CHARGING			5	-- example value
	MINIMUM-FOR-SII								1	-- example value
	MAXIMUM-FOR-SII								5	-- example value
	MINIMUM-FOR-SF-BILLING-CHARGING				1	-- example value
	MAXIMUM-FOR-SF-BILLING-CHARGING				5	-- example value
	MINIMUM-FOR-USI-INFORMATION					1	-- example value
	MAXIMUM-FOR-USI-INFORMATION					5	-- example value
	MINIMUM-FOR-USI-SERVICE-INDICATOR			1	-- example value
	MAXIMUM-FOR-USI-SERVICE-INDICATOR			5	-- example value
	NUM-OF-BCSM-EVENT							4	-- example value
	NUM-OF-BCUSM-EVENT							4	-- example value
	NUM-OF-CHARGING-EVENT						4	-- example value
	NUM-OF-CSAS									2	-- example value
	NUM-OF-CSS									2	-- example value
	NUM-OF-EXTENSIONS							1	-- example value
	NUM-OF-GENERIC-NUMBERS						2	-- example value
	NUM-OF-IN-SERVICE-COMPATIBILITY-ID			2	-- example value
	NUM-OF-LEGS									2	-- example value
	NUM-OF-MESSAGE-IDS							2	-- example value
	MAXIMUM-FOR-AMOUNT							2	-- example value
	MAXIMUM-FOR-INITIAL-UNIT-INCREMENT			2	-- example value
	MAXIMUM-FOR-SCALING-FACTOR					2	-- example value
	MAXIMUM-FOR-SEGMENTS-PER-DATA-INTERVAL		5	-- example value
	MAXIMUM-FOR-TIME-PER-INTERVAL				5	-- example value
	MAXIMUM-FOR-UNITS-PER-DATA-INTERVAL			5 	-- example value
	MAXIMUM-FOR-UNITS-PER-INTERVAL				5	-- example value
	MAXIMUM-FOR-UB-USER-CREDIT					5	-- example value
	MAXIMUM-FOR-UB-NB-CALL						5	-- example value
}
END

IN-CS2-object-identifiers {ccitt(0) identified-organization(4) etsi(0) inDomain(1) in-network(1) CS2(20) modules(0) in-cs2-object-identifiers(17) version1(0)}
DEFINITIONS ::=
BEGIN
-- This module assigns object identifiers for Modules, Packages, Contracts and AC 
-- for IN CS2

-- For Modules from TCAP, ROS, 
tc-Messages						OBJECT IDENTIFIER ::= 	
	{ccitt recommendation Q.773 modules(2) messages(1) version3(3)}
tc-NotationExtensions			OBJECT IDENTIFIER ::= 	
	{ccitt recommendation Q.775 modules(2) notation-extension (4) version1(1)}
ros-InformationObjects			OBJECT IDENTIFIER ::= 	
	{joint-iso-ccitt remote-operations(4) informationObjects(5) version1(0)}
ros-genericPDUs					OBJECT IDENTIFIER ::= 	
	{joint-iso-ccitt remote-operations(4) generic-ROS-PDUs(6) version1(0)}
ros-UsefulDefinitions			OBJECT IDENTIFIER ::= 	
	{joint-iso-ccitt remote-operations(4) useful-definitions(7) version1(0)}
sese-APDUs						OBJECT IDENTIFIER ::= 	
	{joint-iso-ccitt genericULS(20) modules(1) seseAPDUs(6)}
guls-Notation					OBJECT IDENTIFIER ::= 	
	{joint-iso-ccitt genericULS (20) modules (1) notation (1)}
guls-SecurityTransformations	OBJECT IDENTIFIER ::= 	
	{joint-iso-ccitt genericULS (20) modules (1) gulsSecurityTransformations (3)}
ds-UsefulDefinitions			OBJECT IDENTIFIER ::= 	
	{joint-iso-ccitt ds(5) module(1) usefulDefinitions(0) 3}
spkmGssTokens					OBJECT IDENTIFIER ::= 	
	{iso(1) identified-organization(3) dod(6) internet(1) security(5) mechanisms(5) spkm(1) spkmGssTokens(10)}

-- For IN-CS1 Modules
contexts						OBJECT IDENTIFIER ::= 	
	{ccitt(0) identified-organization(4) etsi(0) inDomain(1) in-network(1) CS2(20) modules (0) contexts (8) selectedContexts (1) version (1)}

-- For IN CS2 Modules
datatypes						OBJECT IDENTIFIER ::= 	
	{ccitt(0) identified-organization(4) etsi(0) inDomain(1) in-network(1) CS2(20) modules(0) in-cs2-datatypes (0) version1(0)}
errortypes						OBJECT IDENTIFIER ::= 	
	{ccitt(0) identified-organization(4) etsi(0) inDomain(1) in-network(1) CS2(20) modules(0) in-cs2-errortypes (1) version1(0)}
operationcodes					OBJECT IDENTIFIER ::= 	
	{ccitt(0) identified-organization(4) etsi(0) inDomain(1) in-network(1) CS2(20) modules(0) in-cs2-operationcodes (2) version1(0)}
errorcodes						OBJECT IDENTIFIER ::= 	
	{ccitt(0) identified-organization(4) etsi(0) inDomain(1) in-network(1) CS2(20) modules(0) in-cs2-errorcodes (3) version1(0)}
classes							OBJECT IDENTIFIER ::= 	
	{ccitt(0) identified-organization(4) etsi(0) inDomain(1) in-network(1) CS2(20) modules(0) in-cs2-classes (4) version1(0)}
ssf-scf-Operations				OBJECT IDENTIFIER ::= 	
	{ccitt(0) identified-organization(4) etsi(0) inDomain(1) in-network(1) CS2(20) modules(0) in-cs2-ssf-scf-ops-args (5) version1(0)}
ssf-scf-Protocol				OBJECT IDENTIFIER ::= 	
	{ccitt(0) identified-organization(4) etsi(0) inDomain(1) in-network(1) CS2(20) modules(0) in-cs2-ssf-scf-pkgs-contracts-acs (6) version1(0)}
scf-srf-Operations				OBJECT IDENTIFIER ::= 	
	{ccitt recommendation q 1228 modules(0) in-cs2-scf-srf-ops-args (7) version1(0)}
scf-srf-Protocol				OBJECT IDENTIFIER ::= 	
	{ccitt recommendation q 1228 modules(0) in-cs2-scf-srf-pkgs-contracts-acs(8) version1(0)}
sdf-InformationFramework 		OBJECT IDENTIFIER ::= 	
	{ccitt recommendation q 1228 module(0) sdfInformationFramework(9) version1(0)}
sdf-BasicAccessControl 			OBJECT IDENTIFIER ::= 	
	{ccitt recommendation q 1228 module(0) sdfBasicAccessControl(10) version1(0)}
scf-sdf-Operations				OBJECT IDENTIFIER ::= 	
	{ccitt recommendation q 1228 module(0) scf-sdf-operations(11) version1(0)}
scf-sdf-Protocol 				OBJECT IDENTIFIER ::= 	
	{ccitt recommendation q 1218 modules(0) in-scf-sdf-protocol(12) version1(0)} 
scf-scf-Operations				OBJECT IDENTIFIER ::= 	
	{ccitt recommendation q 1228 modules(0) in-cs2-scf-scf-ops-args (13) version1(0)}
scf-scf-Protocol				OBJECT IDENTIFIER ::= 	
	{ccitt recommendation q 1228 modules(0) in-cs2-scf-scf-pkgs-contracts-acs (14) version1(0)} 
scf-cusf-Operations				OBJECT IDENTIFIER ::= 	
	{ccitt(0) identified-organization(4) etsi(0) inDomain(1) in-network(1) CS2(20) modules(0) in-cs2-scf-cusf-ops-args (15) version1(0)}
scf-cusf-Protocol	O			BJECT IDENTIFIER ::= 	
	{ccitt(0) identified-organization(4) etsi(0) inDomain(1) in-network(1) CS2(20) modules(0) in-cs2-scf-cusf-pkgs-contracts-acs (16) version1(0)}
object-identifiers				OBJECT IDENTIFIER ::= 	
	{ccitt recommendation q 1228 modules(0) in-cs2-object-identifiers(17) version1(0)}
sdf-sdf-Protocol 				OBJECT IDENTIFIER ::= 	
	{ccitt recommendation q 1228 module(0) in-cs2-sdf-sdf-Protocol(18) version1(0)} 


id-cs2				OBJECT IDENTIFIER ::= {ccitt recommendation q 1228 cs2 (2)}
id-cs20E			OBJECT IDENTIFIER ::= 
	{ccitt(0) identified-organization(4) etsi(0) inDomain(1) in-network(1) CS2(20)}



id-ac										OBJECT IDENTIFIER ::= {id-cs2 		ac(3)}
id-acE										OBJECT IDENTIFIER ::= {id-cs20E 	ac(3)}
id-as										OBJECT IDENTIFIER ::= {id-cs2 		as(5)}
id-asE										OBJECT IDENTIFIER ::= {id-cs20E 	as(5)}
id-rosObject								OBJECT IDENTIFIER ::= {id-cs2		rosObject(25)}
id-contract									OBJECT IDENTIFIER ::= {id-cs2 		contract(26)}
id-contractE								OBJECT IDENTIFIER ::= {id-cs20E 	contract(26)}
id-package									OBJECT IDENTIFIER ::= {id-cs2 		package(27)}
id-packageE									OBJECT IDENTIFIER ::= {id-cs20E 	package(27)}

-- for ac, as, rosObject, contract and package, the values are identical to Q1218

id-package-scf-scfConnection				OBJECT IDENTIFIER ::= {id-package 46}
id-package-dsspConnection					OBJECT IDENTIFIER ::= {id-package 47}


-- ROS Objects

id-rosObject-scf							OBJECT IDENTIFIER ::= {id-rosObject 4}
id-rosObject-ssf							OBJECT IDENTIFIER ::= {id-rosObject 5}
id-rosObject-srf							OBJECT IDENTIFIER ::= {id-rosObject 6}
id-rosObject-cusf							OBJECT IDENTIFIER ::= {id-rosObject 7}
id-rosObject-dssp							OBJECT IDENTIFIER ::= {id-rosObject 8}
id-rosObject-sdf							OBJECT IDENTIFIER ::= {id-rosObject 9}

id-rosObject-dua 							OBJECT IDENTIFIER ::= {id-rosObject 1} 
id-rosObject-directory 						OBJECT IDENTIFIER ::= {id-rosObject 2} 
id-rosObject-dapDSA 						OBJECT IDENTIFIER ::= {id-rosObject 3} 

id-rosObject-dspDSA							OBJECT IDENTIFIER ::= {id-rosObject 10} 
id-rosObject-initiatingConsumerDSA			OBJECT IDENTIFIER ::= {id-rosObject 11} 
id-rosObject-respondingSupplierDSA			OBJECT IDENTIFIER ::= {id-rosObject 12} 
id-rosObject-respondingConsumerDSA			OBJECT IDENTIFIER ::= {id-rosObject 13} 
id-rosObject-initiatingSupplierDSA			OBJECT IDENTIFIER ::= {id-rosObject 14} 


-- ssf/scf AC
id-ac-cs2-ssf-scfGenericAC					OBJECT IDENTIFIER ::= {id-acE 4}
id-ac-cs2-ssf-scfAssistHandoffAC			OBJECT IDENTIFIER ::= {id-acE 6}
id-ac-cs2-ssf-scfServiceManagementAC		OBJECT IDENTIFIER ::= {id-acE 7}
id-ac-cs2-scf-ssfGenericAC					OBJECT IDENTIFIER ::= {id-acE 8}
id-ac-cs2-scf-ssfTrafficManagementAC		OBJECT IDENTIFIER ::= {id-acE 10}
id-ac-cs2-scf-ssfServiceManagementAC		OBJECT IDENTIFIER ::= {id-acE 11}
id-ac-cs2-scf-ssfTriggerManagementAC		OBJECT IDENTIFIER ::= {id-acE 13}

-- srf/scf AC
id-ac-srf-scf								OBJECT IDENTIFIER ::= {id-ac 14}

-- 	SCF-SDF - ACs -- 
id-ac-indirectoryAccessAC					OBJECT IDENTIFIER ::= {id-ac 1}
id-ac-indirectoryAccessWith3seAC			OBJECT IDENTIFIER ::= {id-ac 2}
id-ac-inExtendedDirectoryAccessAC			OBJECT IDENTIFIER ::= {id-ac 3}
id-ac-inExtendedDirectoryAccessWith3seAC	OBJECT IDENTIFIER ::= {id-ac 27}

--	SDF - SDF ACs
id-ac-indirectorySystemAC					OBJECT IDENTIFIER ::= {id-ac 15} 
id-ac-inShadowSupplierInitiatedAC			OBJECT IDENTIFIER ::= {id-ac 16} 
id-ac-inShadowConsumerInitiatedAC			OBJECT IDENTIFIER ::= {id-ac 17} 
id-ac-indirectorySystemWith3seAC 			OBJECT IDENTIFIER ::= {id-ac 18} 
id-ac-inShadowSupplierInitiatedWith3seAC	OBJECT IDENTIFIER ::= {id-ac 19} 
id-ac-inShadowConsumerInitiatedWith3seAC	OBJECT IDENTIFIER ::= {id-ac 20} 

-- scf/scf AC
id-ac-scf-scfOperationsAC					OBJECT IDENTIFIER ::= {id-ac 21}
id-ac-distributedSCFSystemAC				OBJECT IDENTIFIER ::= {id-ac 22}
id-ac-scf-scfOperationsWith3seAC			OBJECT IDENTIFIER ::= {id-ac 23}
id-ac-distributedSCFSystemWith3seAC			OBJECT IDENTIFIER ::= {id-ac 24}

-- cusf/scf AC
id-ac-scf-cusf								OBJECT IDENTIFIER ::= {id-acE 25}
id-ac-cusf-scf								OBJECT IDENTIFIER ::= {id-acE 26}


-- ssf/scf Contracts
id-inCs2SsfToScfGeneric						OBJECT IDENTIFIER ::= {id-contractE 3}
id-inCs2AssistHandoffssfToScf				OBJECT IDENTIFIER ::= {id-contractE 5}
id-inCs2ScfToSsfGeneric						OBJECT IDENTIFIER ::= {id-contractE 6}
id-inCs2ScfToSsfTrafficManagement			OBJECT IDENTIFIER ::= {id-contractE 8}
id-inCs2ScfToSsfServiceManagement			OBJECT IDENTIFIER ::= {id-contractE 9}
id-inCs2SsfToScfServiceManagement			OBJECT IDENTIFIER ::= {id-contractE 10}
id-inCs2ScfToSsfTriggerManagement			OBJECT IDENTIFIER ::= {id-contractE 12}

-- srf/scf Contracts
id-contract-srf-scf							OBJECT IDENTIFIER ::= {id-contract 13}

-- 	SCF-SDF contracts -- 
id-contract-dap 							OBJECT IDENTIFIER ::= {id-contract 1} 
id-contract-dapExecute						OBJECT IDENTIFIER ::= {id-contract 2} 

-- 	SDF - SDF Contracts. 
id-contract-indsp							OBJECT IDENTIFIER ::= {id-contract 14} 
id-contract-shadowConsumer					OBJECT IDENTIFIER ::= {id-contract 15} 
id-contract-shadowSupplier					OBJECT IDENTIFIER ::= {id-contract 17} 

-- scf/scf Contracts
id-contract-scf-scf							OBJECT IDENTIFIER ::= {id-contract 18}
id-contract-dssp							OBJECT IDENTIFIER ::= {id-contract 19}

-- cusf/scf Contracts
id-contract-scf-cusf						OBJECT IDENTIFIER ::= {id-contractE 20}
id-contract-cusf-scf						OBJECT IDENTIFIER ::= {id-contractE 21}

-- ssf/scf Operation Packages
id-package-scfActivation					OBJECT IDENTIFIER ::= {id-package 11}
id-package-srf-scfActivationOfAssist		OBJECT IDENTIFIER ::= {id-package 15} 
id-package-assistConnectionEstablishment	OBJECT IDENTIFIER ::= {id-package 16} 
id-package-genericDisconnectResource		OBJECT IDENTIFIER ::= {id-package 17} 
id-package-nonAssistedConnectionEstablishment
											OBJECT IDENTIFIER ::= {id-package 18} 
id-package-connect							OBJECT IDENTIFIER ::= {id-package 19} 
id-package-callHandling						OBJECT IDENTIFIER ::= {id-packageE 20} 
id-package-bcsmEventHandling				OBJECT IDENTIFIER ::= {id-package 21} 
id-package-chargingEventHandling			OBJECT IDENTIFIER ::= {id-package 23} 
id-package-ssfCallProcessing				OBJECT IDENTIFIER ::= {id-packageE 24} 
id-package-scfCallInitiation				OBJECT IDENTIFIER ::= {id-package 25} 
id-package-timer							OBJECT IDENTIFIER ::= {id-package 26} 
id-package-billing							OBJECT IDENTIFIER ::= {id-package 27} 
id-package-charging							OBJECT IDENTIFIER ::= {id-package 28} 
id-package-trafficManagement				OBJECT IDENTIFIER ::= {id-package 29} 
id-package-serviceManagementActivate		OBJECT IDENTIFIER ::= {id-package 30} 
id-package-serviceManagementResponse		OBJECT IDENTIFIER ::= {id-package 31} 
id-package-callReport						OBJECT IDENTIFIER ::= {id-package 32} 
id-package-signallingControl				OBJECT IDENTIFIER ::= {id-package 33} 
id-package-activityTest						OBJECT IDENTIFIER ::= {id-package 34} 
id-package-cancel							OBJECT IDENTIFIER ::= {id-packageE 36} 
id-package-cphResponse						OBJECT IDENTIFIER ::= {id-packageE 37} 
id-package-entityReleased					OBJECT IDENTIFIER ::= {id-package 38}
id-package-triggerManagement				OBJECT IDENTIFIER ::= {id-package 39}
id-package-uSIHandling						OBJECT IDENTIFIER ::= {id-package 40}

-- srf/scf Operation Packages
id-package-specializedResourceControl		OBJECT IDENTIFIER ::= {id-package 42}
id-package-srf-scfCancel					OBJECT IDENTIFIER ::= {id-package 43}
id-package-messageControl 					OBJECT IDENTIFIER ::= {id-package 44}
id-package-scriptControl 					OBJECT IDENTIFIER ::= {id-package 45}

-- 	SCF-SDF packages --
id-package-search 							OBJECT IDENTIFIER ::= {id-package 2} 
id-package-modify 							OBJECT IDENTIFIER ::= {id-package 3} 
id-package-dapConnection					OBJECT IDENTIFIER ::= {id-package 10}
id-package-execute							OBJECT IDENTIFIER ::= {id-package 4} 

-- 	SDF - SDF Packages. 
id-package-dspConnection					OBJECT IDENTIFIER ::= {id-package 47} 
id-package-inchainedModify					OBJECT IDENTIFIER ::= {id-package 48} 
id-package-inchainedSearch					OBJECT IDENTIFIER ::= {id-package 49} 
id-package-chainedExecute					OBJECT IDENTIFIER ::= {id-package 50} 
id-package-dispConnection					OBJECT IDENTIFIER ::= {id-package 51} 
id-package-shadowConsumer					OBJECT IDENTIFIER ::= {id-package 52} 
id-package-shadowSupplier					OBJECT IDENTIFIER ::= {id-package 53} 

-- scf/scf Operation Packages
id-package-handlingInformation				OBJECT IDENTIFIER ::= {id-package 54}
id-package-notification						OBJECT IDENTIFIER ::= {id-package 55}
id-package-chargingInformation				OBJECT IDENTIFIER ::= {id-package 56}
id-package-userInformation					OBJECT IDENTIFIER ::= {id-package 57}
id-package-networkCapability				OBJECT IDENTIFIER ::= {id-package 58}
id-package-chainedSCFOperations				OBJECT IDENTIFIER ::= {id-package 59}

-- cusf/scf Operation Packages
id-package-emptyConnection					OBJECT IDENTIFIER ::= {id-package 60}
id-package-basic-cusf-scf					OBJECT IDENTIFIER ::= {id-packageE 61}
id-package-basic-scf-cusf					OBJECT IDENTIFIER ::= {id-packageE 62}


-- ssf/scf Abstract Syntaxes

id-as-ssf-scfGenericAS						OBJECT IDENTIFIER ::= {id-asE 4}
id-as-assistHandoff-ssf-scfAS				OBJECT IDENTIFIER ::= {id-asE 6}
id-as-scf-ssfGenericAS						OBJECT IDENTIFIER ::= {id-asE 7}
id-as-scf-ssfTrafficManagementAS			OBJECT IDENTIFIER ::= {id-asE 9}
id-as-scf-ssfServiceManagementAS			OBJECT IDENTIFIER ::= {id-asE 10}
id-as-ssf-scfServiceManagementAS			OBJECT IDENTIFIER ::= {id-asE 11}
id-as-scf-ssfTriggerManagementAS			OBJECT IDENTIFIER ::= {id-asE 13}


-- srf/scf Abstract Syntaxes
id-as-basic-srf-scf							OBJECT IDENTIFIER ::= {id-as 14}
id-as-basic-scf-srf							OBJECT IDENTIFIER ::= {id-as 15}

-- 	SCF-SDF - abstract syntaxes 
id-as-indirectoryOperationsAS 				OBJECT IDENTIFIER ::= {id-as 1}
id-as-indirectoryBindingAS					OBJECT IDENTIFIER ::= {id-as 2}
id-as-inExtendedDirectoryOperationsAS 		OBJECT IDENTIFIER ::= {id-as 3} 
id-as-inSESEAS 								OBJECT IDENTIFIER ::= {id-as 25}

-- SDF-SDF - abstract syntaxes
id-as-indirectorySystemAS					OBJECT IDENTIFIER ::= {id-as 16} 
id-as-indirectoryDSABindingAS				OBJECT IDENTIFIER ::= {id-as 17} 
id-as-indirectoryShadowAS					OBJECT IDENTIFIER ::= {id-as 18} 
id-as-indsaShadowBindingAS					OBJECT IDENTIFIER ::= {id-as 19} 

-- scf/scf Abstract Syntaxes
id-as-scf-scfOperationsAS					OBJECT IDENTIFIER ::= {id-as 20}
id-as-distributedSCFSystemAS				OBJECT IDENTIFIER ::= {id-as 21}
id-as-scf-scfBindingAS						OBJECT IDENTIFIER ::= {id-as 22}


-- cusf/scf Abstract Syntaxes
id-as-basic-cusf-scf						OBJECT IDENTIFIER ::= {id-asE 23}
id-as-basic-scf-cusf						OBJECT IDENTIFIER ::= {id-asE 24}



-- Object Identifiers for SDF-SDF interface
-- useful definitions
in-ds 					OBJECT IDENTIFIER ::= {ccitt recommendation q 1228 sdf-objects (10)}
id-avc					OBJECT IDENTIFIER ::= {in-ds 29}
id-aca					OBJECT IDENTIFIER ::= {in-ds 24}
id-soa					OBJECT IDENTIFIER ::= {in-ds 21}

-- Object Identifiers for SDF-SDF interface. 

-- 	SDF Attributes
id-soa-methodRuleUse						OBJECT IDENTIFIER ::= {id-soa 1} 
id-aca-prescriptiveACI 						OBJECT IDENTIFIER ::= {id-aca 4}
id-aca-entryACI 							OBJECT IDENTIFIER ::= {id-aca 5}
id-aca-subentryACI 							OBJECT IDENTIFIER ::= {id-aca 6}

-- 	SDF Attribute Value Contexts
id-avc-assignment 							OBJECT IDENTIFIER ::= {id-avc 1} 

END

IN-CS2-SSF-SCF-ops-args {ccitt(0) identified-organization(4) etsi(0) inDomain(1) in-network(1) CS2(20) modules(0) in-cs2-ssf-scf-ops-args (5) version1(0)}
DEFINITIONS IMPLICIT TAGS::= 
BEGIN
IMPORTS

	errortypes, datatypes, operationcodes, classes, ros-InformationObjects
FROM IN-CS2-object-identifiers

	{ccitt(0) identified-organization(4) etsi(0) inDomain(1) in-network(1) CS2(20) modules(0) in-cs2-object-identifiers(17) version1(0)}
	OPERATION
FROM Remote-Operations-Information-Objects ros-InformationObjects

tc-Messages, classes FROM IN-CS2-object-identifiers	
		{ccitt(0) identified-organization(4) etsi(0) inDomain(1) in-network(1) CS2(20) module(0) in-cs2-object-identifiers(17) version1(0)}
	InvokeIdType
FROM TCAPMessages tc-Messages 

	AddOnChargingInformation,
	ChargingTariffInformation,
	ChargingMessageType
FROM Tarifing-DataTypes {itu-t(0) identified-organization etsi (0) 1296 version1(1)};

	IMSI,
	Ext-BasicServiceCode
FROM MAP-CommonDataTypes {ccitt(0) identified-organization(4) etsi(0) mobileDomain(0)
gsm-Network(1) modules(3) map-CommonDataTypes(18) version3(3)}

	LocationInformation,
	SubscriberState
FROM MAP-MS-DataTypes {ccitt(0) identified-organization(4) etsi(0) mobileDomain(0)
gsm-Network(1) modules(3) map-MS-DataTypes(11) version3(3)}

	CallReferenceNumber,
	SuppressionOfAnnouncement
FROM MAP-CH-DataTypes {ccitt(0) identified-organization(4) etsi(0) mobileDomain(0)
gsm-Network(1) modules(3) map-CH-DataTypes(13) version3(3)}

	ISDN-AddressString
FROM MAP-CommonDataTypes {ccitt identified-organization(4) etsi(0) mobileDomain(0)
gsm-Network (1) modules (3) map-CommonDataTypes (18) version3 (3)}

		PARAMETERS-BOUND
FROM IN-CS2-classes classes

	opcode-activateServiceFiltering,
	opcode-activityTest,
	opcode-applyCharging,
	opcode-applyChargingReport,
	opcode-assistRequestInstructions,
	opcode-callGap,
	opcode-callInformationReport,
	opcode-callInformationRequest,
	opcode-cancel,
	opcode-collectInformation,
	opcode-connect,
	opcode-connectToResource,
	opcode-continue,
	opcode-continueWithArgument,
	opcode-createCallSegmentAssociation,
	opcode-disconnectForwardConnection,
	opcode-dFCWithArgument,
	opcode-disconnectLeg,
	opcode-entityReleased,
	opcode-establishTemporaryConnection,
	opcode-eventNotificationCharging,
	opcode-eventReportBCSM,
	opcode-furnishChargingInformation,
	opcode-initialDP,
	opcode-initiateCallAttempt,
	opcode-manageTriggerData,
	opcode-mergeCallSegments,
	opcode-moveCallSegments,
	opcode-moveLeg,
	opcode-releaseCall,
	opcode-reportUTSI,
	opcode-requestNotificationChargingEvent,
	opcode-requestReportBCSMEvent,
	opcode-requestReportUTSI,
	opcode-resetTimer,
	opcode-sendChargingInformation,
	opcode-sendSTUI,
	opcode-serviceFilteringResponse,
	opcode-splitLeg
FROM IN-CS2-operationcodes operationcodes

	ActionIndicator,
	ActionPerformed,
	AChBillingChargingCharacteristics {},
	AdditionalCallingPartyNumber {},
	AlertingPattern,
	AssistingSSPIPRoutingAddress {},
	BackwardGVNS {},
	BCSMEvent {},
	BearerCapability {},
	CalledPartyNumber {},
	CallingPartyBusinessGroupID{},
	CallingPartyNumber {},
	CallingPartysCategory,
	CallingPartySubaddress{},
	CallResult {},
	CallSegmentID {},
	Carrier{},
	Cause {},
	CGEncountered,
	ChargingEvent {},
	ControlType,
	CorrelationID {},
	CountersValue,
	CSAID {},
	CutAndPaste,
	DateAndTime,
	DestinationRoutingAddress {},
	Digits {},
	DisplayInformation {},
	EventSpecificInformationBCSM {},
	EventSpecificInformationCharging {},
	EventTypeBCSM,
	EventTypeCharging {},
	ExtensionField {},
	FCIBillingChargingCharacteristics {},
	FilteredCallTreatment {},
	FilteringCharacteristics,
	FilteringCriteria {},
	FilteringTimeOut,
	ForwardCallIndicators,
	ForwardGVNS {},
	GapCriteria {},
	GapIndicators,
	GapTreatment {},
	GenericName {},
	GenericNumbers {},
	HighLayerCompatibility,
	initialCallSegment,
	INServiceCompatibilityIndication {},
	INServiceCompatibilityResponse,
	Integer4,
	InvokeID,
	IPAvailable {},
	IPRoutingAddress {},
	IPSSPCapabilities {},
	ISDNAccessRelatedInformation{},
	LegID,
	leg1,
	LocationNumber {},
	MiscCallInfo,
	MonitorMode,
	NumberingPlan,
	OriginalCalledPartyID {},
	Reason {},
	RedirectingPartyID {},
	RedirectionInformation,
	RegistratorIdentifier{},
	RequestedInformationList {},
	RequestedInformationTypeList,
	RequestedUTSIList {},
	ResponseCondition,
	RouteList {},
	ScfID {},
	SCIBillingChargingCharacteristics {},
	ServiceInteractionIndicators {},
	ServiceInteractionIndicatorsTwo,
	ServiceKey,
	TerminalType,
	TimerID,
	TimerValue,
	TriggerDataIdentifier {},
	USIInformation {},
	USIServiceIndicator {}
FROM IN-CS2-datatypes datatypes

	cancelFailed,
	eTCFailed,
	improperCallerResponse,
	missingCustomerRecord,
	missingParameter,
	parameterOutOfRange,
	requestedInfoError,
	systemFailure,
	taskRefused,
	unavailableResource,
	unexpectedComponentSequence,
	unexpectedDataValue,
	unexpectedParameter,
	unknownLegID,
	unknownResource
FROM IN-CS2-errortypes errortypes
;

activateServiceFiltering {PARAMETERS-BOUND : bound} OPERATION :: = {
	ARGUMENT		ActivateServiceFilteringArg {bound}
	RETURN RESULT 	TRUE 
	ERRORS 			{missingParameter |
					parameterOutOfRange |
					systemFailure |
					taskRefused |
					unexpectedComponentSequence |
					unexpectedParameter 
					}
	CODE 			opcode-activateServiceFiltering 
	}
-- Direction: SCF --> SSF, Timer: Tasf 
-- When receiving this operation, the SSF handles calls to destination in a specified manner 
-- without sending queries for every detected call. It is used for example for providing 
-- televoting or mass calling services. Simple registration functionality (counters) and 
-- announcement control may be located at the SSF. The operation initializes the specified 
-- counters in the SSF.

ActivateServiceFilteringArg {PARAMETERS-BOUND : bound} ::= SEQUENCE {
	filteredCallTreatment		[0] FilteredCallTreatment {bound},
	filteringCharacteristics	[1] FilteringCharacteristics,
	filteringTimeOut			[2] FilteringTimeOut,
	filteringCriteria			[3] FilteringCriteria {bound},
	startTime					[4] DateAndTime	OPTIONAL,
	extensions					[5] SEQUENCE SIZE(1..bound.&numOfExtensions) OF 
				ExtensionField {bound} OPTIONAL,
	...
	}

activityTest OPERATION ::= {
	RETURN RESULT TRUE
	CODE	opcode-activityTest
	}
-- Direction: SCF --> SSF, Timer: Tat 
-- This operation is used to check for the continued existence of a relationship between the SCF 
-- and SSF. If the relationship is still in existence, then the SSF will respond. If no reply is 
-- received, then the SCF will assume that the SSF has failed in some way and will take the 
-- appropriate action.

applyCharging {PARAMETERS-BOUND : bound} OPERATION ::= {
	ARGUMENT		ApplyChargingArg {bound}
	RETURN RESULT	FALSE
	ERRORS 			{missingParameter |
					unexpectedComponentSequence |
					unexpectedParameter |
					unexpectedDataValue | 
					parameterOutOfRange |
					systemFailure |
					taskRefused|
					unknownLegID}
	CODE			opcode-applyCharging
	}
-- Direction: SCF --> SSF, Timer: Tac
-- This operation is used for interacting from the SCF with the SSF charging mechanisms. 
-- The ApplyChargingReport operation provides the feedback from the SSF to the SCF.

ApplyChargingArg {PARAMETERS-BOUND : bound} ::= SEQUENCE {
	aChBillingChargingCharacteristics	[0] AChBillingChargingCharacteristics {bound},
	sendCalculationToSCPIndication		[1]	BOOLEAN OPTIONAL,
-- This parameter, if present, shall be set to TRUE. The parameter is ingored if CS2 is used.
	partyToCharge						[2] LegID	OPTIONAL,
	extensions							[3] SEQUENCE SIZE (1..bound.&numOfExtensions) OF 
																ExtensionField {bound} 	OPTIONAL,
	...
	}

-- The partyToCharge parameter indicates the party in the call to which the ApplyCharging operation
-- should be applied.

applyChargingReport {PARAMETERS-BOUND : bound} OPERATION ::= {
	ARGUMENT		ApplyChargingReportArg {bound}
	RETURN RESULT	FALSE
	ERRORS		 	{missingParameter |
					unexpectedComponentSequence |
					unexpectedParameter |
					unexpectedDataValue |
					parameterOutOfRange |
					systemFailure |
					taskRefused}
	CODE			opcode-applyChargingReport
	}
-- Direction: SSF --> SCF, Timer: Tacr 
-- This operation is used by the SSF to report to the SCF the occurrence of a 
-- specific charging event as requested by the SCF using the ApplyCharging operation.

ApplyChargingReportArg {PARAMETERS-BOUND : bound} ::= CallResult {bound}

assistRequestInstructions {PARAMETERS-BOUND : bound} OPERATION ::= {
	ARGUMENT		AssistRequestInstructionsArg {bound}
	RETURN RESULT	FALSE
	ERRORS			{missingCustomerRecord|
					missingParameter |
					systemFailure |
					taskRefused |
					unexpectedComponentSequence |
					unexpectedDataValue |
					unexpectedParameter}
	CODE			opcode-assistRequestInstructions
	}
-- Direction: SSF --> SCF or SRF --> SCF, Timer: Tari
-- This operation is used when there is an assist or a hand-off procedure and may be sent by the SSF
-- or SRF to the SCF. This operation is sent by the assisting SSF to SCF, when the initiating SSF 
-- has set up a connection to the SRF or to the assisting SSF as a result of receiving an 
-- EstablishTemporaryConnection or Connect operation (in the case of hand-off) from the SCF.
-- Refer to clause 18 for a description of the procedures associated with this operation.

AssistRequestInstructionsArg {PARAMETERS-BOUND : bound} ::= SEQUENCE {
	correlationID		[0] CorrelationID {bound},
	iPAvailable			[1] IPAvailable {bound}							OPTIONAL,
	iPSSPCapabilities	[2] IPSSPCapabilities {bound}					OPTIONAL,
	extensions			[3] SEQUENCE SIZE(1..bound.&numOfExtensions) OF ExtensionField {bound}
																		OPTIONAL,
	...
	}
-- OPTIONAL denotes network operator specific use. The value of the correlationID may be the 
-- Called Party Number supplied by the initiating SSF.

callGap {PARAMETERS-BOUND : bound} OPERATION :: = {
	ARGUMENT		CallGapArg {bound}
	RETURN RESULT	FALSE
	ALWAYS RESPONDS FALSE
	CODE			opcode-callGap
	}
-- Direction: SCF --> SSF, Timer: Tcg
-- This operation is used to request the SSF to reduce the rate at which specific service requests
-- are sent to the SCF.

CallGapArg {PARAMETERS-BOUND : bound}::= SEQUENCE {
	gapCriteria		[0] GapCriteria {bound},
	gapIndicators	[1] GapIndicators,
	controlType		[2] ControlType														OPTIONAL,
	gapTreatment	[3] GapTreatment {bound}											OPTIONAL,
	extensions		[4] SEQUENCE SIZE(1..bound.&numOfExtensions) OF ExtensionField {bound}
																					 	OPTIONAL,
	...
	}
-- OPTIONAL denotes network operator optional. If gapTreatment is not present, the SSF will use 
-- a default treatment depending on network operator implementation.

callInformationReport {PARAMETERS-BOUND : bound} OPERATION ::= {
	ARGUMENT		CallInformationReportArg {bound}
	RETURN RESULT	FALSE
	ALWAYS RESPONDS	FALSE
	CODE			opcode-callInformationReport
	}
-- Direction: SSF --> SCF, Timer: Tcirp
-- This operation is used to send specific call information for a single call to the SCF as
-- requested by the SCF in a previous CallInformationRequest.

CallInformationReportArg {PARAMETERS-BOUND : bound} ::= SEQUENCE {
	requestedInformationList	[0] RequestedInformationList {bound},
	extensions					[2] SEQUENCE SIZE(1..bound.&numOfExtensions)	OF 
																ExtensionField {bound} 	OPTIONAL,
	legID						[3] LegID	OPTIONAL,
	...
	}
-- OPTIONAL denotes network operator optional.

callInformationRequest {PARAMETERS-BOUND : bound} OPERATION ::= {
	ARGUMENT		CallInformationRequestArg {bound}
	RETURN RESULT	FALSE
	ERRORS 			{missingParameter |
					parameterOutOfRange |
					requestedInfoError |
					systemFailure |
					taskRefused |
					unexpectedComponentSequence |
					unexpectedDataValue | 
					unexpectedParameter|
					unknownLegID}
	CODE			opcode-callInformationRequest
	}
-- Direction: SCF --> SSF, Timer: Tcirq
-- This operation is used to request the SSF to record specific information about a single call and 
-- report it to the SCF (with a CallInformationReport operation). 

CallInformationRequestArg {PARAMETERS-BOUND : bound}::= SEQUENCE {
	requestedInformationTypeList	[0] RequestedInformationTypeList,
	extensions						[2] SEQUENCE SIZE(1..bound.&numOfExtensions) OF 
																ExtensionField {bound} 	OPTIONAL,
	legID							[3] LegID											OPTIONAL,
	...
	}
-- OPTIONAL denotes network operator optional.

cancel {PARAMETERS-BOUND : bound} OPERATION :: = {
	ARGUMENT		CancelArg {bound}
	RETURN RESULT	FALSE
	ERRORS 			{cancelFailed |
					missingParameter |
					taskRefused}
	CODE			opcode-cancel
	}
-- Direction: SCF --> SSF, or SCF --> SRF, Timer: Tcan 
-- This operation cancels the correlated previous operation or all previous requests. The following
-- operations can be canceled: PlayAnnouncement, PromptAndCollectUserInformation,
-- PromptAndReceiveMessage. 

CancelArg {PARAMETERS-BOUND : bound}::= CHOICE {
	invokeID			[0] InvokeID,
	allRequests			[1] NULL,
	callSegmentToCancel	[2] SEQUENCE {
			invokeID		[0] InvokeID,
			callSegmentID	[1] CallSegmentID {bound},
...
			}
	}
-- The InvokeID has the same value as that which was used for the operation to be cancelled.

collectInformation {PARAMETERS-BOUND : bound} OPERATION :: = {
	ARGUMENT		CollectInformationArg {bound}	OPTIONAL TRUE
	RETURN RESULT	FALSE
	ERRORS 			{missingParameter |
					systemFailure |
					taskRefused |
					unexpectedComponentSequence |
					unexpectedDataValue |
					unexpectedParameter}
	CODE			opcode-collectInformation
	}
-- Direction: SCF --> SSF, Timer: Tci
-- This operation is used to request the SSF to perform the originating basic call processing
-- actions to prompt a calling party for destination information, then collect destination
-- information according to a specified numbering plan (e.g. for virtual private networks).

CollectInformationArg {PARAMETERS-BOUND : bound}::= SEQUENCE {
	extensions	[4] SEQUENCE SIZE(1..bound.&numOfExtensions) OF ExtensionField {bound} 	OPTIONAL,
	...
	}

connect {PARAMETERS-BOUND : bound} OPERATION ::= {
	ARGUMENT		ConnectArg {bound}
	RETURN RESULT	FALSE
	ERRORS 			{missingParameter |
					parameterOutOfRange | 
					systemFailure |
					taskRefused |
					unexpectedComponentSequence |
					unexpectedDataValue |
					unexpectedParameter}
	CODE			opcode-connect
	}
-- Direction: SCF --> SSF, Timer: Tcon
-- This operation is used to request the SSF to perform the call processing actions to route or
-- forward a call to a specified destination. To do so, the SSF may or may not use destination 
-- information from the calling party (e.g. dialed digits) and existing call setup information 
-- (e.g. route index to a list of trunk groups), depending on the information provided by the SCF.
-- 	- When address information is only included in the Connect operation, call processing resumes at 
--    the Analyzed_Information PIC in the O-BCSM. 
-- 	- When address information and routing information is included, call processing resumes at the
--	  Select_Route PIC.

ConnectArg {PARAMETERS-BOUND : bound} ::= SEQUENCE {
	destinationRoutingAddress		[0] DestinationRoutingAddress {bound},
	alertingPattern	[1] AlertingPattern	OPTIONAL,
	correlationID					[2] CorrelationID {bound}					OPTIONAL,
	cutAndPaste	[3] CutAndPaste	OPTIONAL,
	iSDNAccessRelatedInformation	[5] ISDNAccessRelatedInformation{bound}		OPTIONAL,
	originalCalledPartyID			[6] OriginalCalledPartyID {bound}			OPTIONAL,
	routeList						[7] RouteList {bound}						OPTIONAL,
	scfID							[8] ScfID {bound}							OPTIONAL,
	extensions	[10] SEQUENCE SIZE(1..bound.&numOfExtensions) OF 
		    ExtensionField {bound} 	OPTIONAL,
	carrier							[11] Carrier{bound}							OPTIONAL,
	serviceInteractionIndicators	[26] ServiceInteractionIndicators {bound}	OPTIONAL,
	callingPartyNumber				[27] CallingPartyNumber {bound}				OPTIONAL,
	callingPartysCategory	[28] CallingPartysCategory	OPTIONAL,
	redirectingPartyID				[29] RedirectingPartyID {bound}				OPTIONAL,
	redirectionInformation	[30] RedirectionInformation	OPTIONAL,
	displayInformation				[12] DisplayInformation {bound}				OPTIONAL,
	forwardCallIndicators	[13] ForwardCallIndicators	OPTIONAL,
	genericNumbers					[14] GenericNumbers {bound}					OPTIONAL,
	serviceInteractionIndicatorsTwo	[15] ServiceInteractionIndicatorsTwo	OPTIONAL,
	iNServiceCompatibilityResponse	[16] INServiceCompatibilityResponse	OPTIONAL,
	forwardGVNS						[17] ForwardGVNS {bound}					OPTIONAL,
	backwardGVNS					[18] BackwardGVNS {bound}					OPTIONAL,
	callSegmentID	[20] CallSegmentID {bound}	OPTIONAL,
	legToBeCreated	[21] LegID	OPTIONAL,
	locationNumber					[50] LocationNumber {bound}					OPTIONAL,
	bearerCapability				[51] BearerCapability {bound}				OPTIONAL,
	suppressionOfAnnouncement	[55] SuppressionOfAnnouncement	OPTIONAL,
	oCSIApplicable	[56] OCSIApplicable	OPTIONAL,
	...
	}

connectToResource {PARAMETERS-BOUND : bound} OPERATION ::= {
	ARGUMENT		ConnectToResourceArg {bound}
	RETURN RESULT	FALSE
	ERRORS 			{missingParameter |
					systemFailure |
					taskRefused |
					unexpectedComponentSequence |
					unexpectedDataValue |
					unexpectedParameter|
					unknownLegID}
	CODE			opcode-connectToResource
	}
-- Direction: SCF --> SSF, Timer: Tctr
-- This operation is used to connect a call from the SSP to the physical entity containing the SRF. 
-- Refer to clause 18 for a description of the procedures associated with this operation.

ConnectToResourceArg {PARAMETERS-BOUND : bound} ::= SEQUENCE {
	resourceAddress	CHOICE {
		ipRoutingAddress			[0] IPRoutingAddress {bound},
		legID						[1] LegID,
		ipAddressAndLegID			[2] SEQUENCE {
			 ipRoutingAddress			[0] IPRoutingAddress {bound},
			 legID						[1] LegID,
...
			},
		none						[3] NULL,
		callSegmentID				[5] CallSegmentID {bound},
		ipAddressAndCallSegment		[6] SEQUENCE {
			ipRoutingAddress			[0] IPRoutingAddress {bound},
			callSegmentID				[1] CallSegmentID {bound},
...
			}
		},
	extensions						[4] SEQUENCE SIZE(1..bound.&numOfExtensions) OF
																ExtensionField {bound}	OPTIONAL,
	serviceInteractionIndicators	[30] ServiceInteractionIndicators {bound}			OPTIONAL,
	serviceInteractionIndicatorsTwo	[7] ServiceInteractionIndicatorsTwo					OPTIONAL,
	...
	}

continue OPERATION ::= {
	RETURN RESULT	FALSE
	ALWAYS RESPONDS	FALSE
	CODE			opcode-continue
	}
-- Direction: SCF --> SSF, Timer: Tcue
-- This operation is used to request the SSF to proceed with call processing at the DP at which it 
-- previously suspended call processing to await SCF instructions (i.e. proceed to the next point 
-- in call in the BCSM). The SSF continues call processing without substituting new data from SCF.
-- This operation is not valid for a single call segment CSA with more than 2 legs or a multi call
--  segment CSA

continueWithArgument {PARAMETERS-BOUND : bound} OPERATION ::= {
	ARGUMENT		ContinueWithArgumentArg {bound}
	RETURN RESULT	FALSE
	ERRORS			{missingParameter |
					unknownLegID |
					unexpectedComponentSequence |
					unexpectedParameter |
					unexpectedDataValue}
	CODE			opcode-continueWithArgument
	}
-- Direction: SCF --> SSF, Timer: Tcwa
-- This operation is used to request the SSF to proceed with call processing at the DP a which it
-- previously suspended call processing to await SCF instructions. 
-- It is also used to provide additional service related information to a User 
-- (Called Party or Calling Party) whilst the call processing proceeds.

ContinueWithArgumentArg {PARAMETERS-BOUND : bound} ::= SEQUENCE {
	legorCSID	CHOICE{
	legID							[0] LegID,
	csID							[9] CallSegmentID {bound}}	DEFAULT legID: sendingSideID: leg1,
	alertingPattern					[1] AlertingPattern					OPTIONAL,
	genericName						[2] GenericName {bound}				OPTIONAL,
	iNServiceCompatibilityResponse	[3] INServiceCompatibilityResponse	OPTIONAL,
	forwardGVNS						[4] ForwardGVNS {bound}				OPTIONAL,
	backwardGVNS					[5] BackwardGVNS {bound}			OPTIONAL,
	extensions						[6] SEQUENCE SIZE (1..bound.&numOfExtensions) OF
												ExtensionField {bound}	OPTIONAL,
	serviceInteractionIndicatorsTwo	[7] ServiceInteractionIndicatorsTwo	OPTIONAL,
	locationNumber					[51] LocationNumber {bound}			OPTIONAL,
	...
	}

createCallSegmentAssociation {PARAMETERS-BOUND : bound} OPERATION ::= {
	ARGUMENT	CreateCallSegmentAssociationArg {bound}	OPTIONAL TRUE
	RESULT		CreateCallSegmentAssociationResult {bound}
	ERRORS		{missingParameter |
				systemFailure|
				taskRefused|
				unexpectedComponentSequence |
				unexpectedDataValue |
				unexpectedParameter}
	CODE		opcode-createCallSegmentAssociation
	}
-- Direction SCF --> SSF, Timer Tcsa 
-- This operation is used to create a new CSA. The new CSA will not contain any Call Segments after
-- creation. The SSF is responsible for specifying a new CSA identifier for the created CSA which is
-- unique within the SSF.

CreateCallSegmentAssociationArg {PARAMETERS-BOUND : bound} ::= SEQUENCE {
	extensions				[0] SEQUENCE SIZE {1..bound.&numOfExtensions) OF ExtensionField {bound}
																						OPTIONAL,
	...
	}
CreateCallSegmentAssociationResult {PARAMETERS-BOUND : bound} ::= SEQUENCE {
	newCallSegmentAssociation	[0] CSAID {bound},
	extensions					[1] SEQUENCE SIZE {1..bound.&numOfExtensions) OF 
																ExtensionField {bound}	OPTIONAL,
	...
	}

disconnectForwardConnection OPERATION ::= {
	RETURN RESULT	FALSE
	ERRORS 			{systemFailure |
					taskRefused |
					unexpectedComponentSequence}
	CODE			opcode-disconnectForwardConnection
	}
-- Direction: SCF --> SSF, Timer: Tdfc
-- This operation is used to disconnect a forward temporary connection or a connection to a
-- resource. Refer to clause 18 for a description of the procedures associated with this operation.
-- This operation is not valid for a multi call segment CSA.

disconnectForwardConnectionWithArgument {PARAMETERS-BOUND : bound} OPERATION ::= {
	ARGUMENT		DisconnectForwardConnectionWithArgumentArg {bound}
	RETURN RESULT	FALSE
	ERRORS 		{missingParameter |
				systemFailure |
				taskRefused |
				unexpectedComponentSequence |
				unexpectedDataValue |
				unexpectedParameter |
				unknownLegID}
	CODE		opcode-dFCWithArgument
	}
-- Direction: SCF --> SSF, Timer: Tdfcwa
-- This operation is used to disconnect a forward temporary connection or a connection to a
-- resource. 
-- Refer to clause 18 for a description of the procedures associated with this operation. 

DisconnectForwardConnectionWithArgumentArg {PARAMETERS-BOUND : bound}::= SEQUENCE {
	partyToDisconnect	CHOICE {
			legID			[0] LegID,
			callSegmentID	[1] CallSegmentID {bound}
			},
	extensions	[2] SEQUENCE SIZE (1..bound.&numOfExtensions) OF ExtensionField {bound} OPTIONAL,
	...
	}

disconnectLeg {PARAMETERS-BOUND : bound} OPERATION :: = {
	ARGUMENT		DisconnectLegArg {bound}
	RETURN RESULT TRUE	
	ERRORS 			{missingParameter|
					systemFailure |
					taskRefused |
					unexpectedComponentSequence |
					unexpectedDataValue |
					unexpectedParameter|
					unknownLegID}
	CODE			opcode-disconnectLeg
	}
--	Direction: SCF --> SSF. Timer: T dl
--	This operation is issued by the SCF to release a specific leg associated with the call and
--  retain any other legs not specified in the DisconnectLeg. Any leg may be disconnected,
--  including the controlling leg, without completely releasing all legs.
--	Refer to clause 18 for a description of the procedures associated with this operation. 

DisconnectLegArg {PARAMETERS-BOUND : bound} ::= SEQUENCE {
	legToBeReleased	[0] LegID,
	releaseCause	[1] Cause {bound}													OPTIONAL,
	extensions		[2] SEQUENCE SIZE (1..bound.&numOfExtensions) OF ExtensionField {bound}
																						OPTIONAL,
	...
	}


entityReleased {PARAMETERS-BOUND : bound} OPERATION ::= {
	ARGUMENT		EntityReleasedArg {bound}
	RETURN RESULT	FALSE
	ALWAYS RESPONDS FALSE
	CODE			opcode-entityReleased
	}
-- Direction SSF --> SCF, Timer: Ter
-- This operation is used by SSF to inform the SCF of an error/exception.

EntityReleasedArg {PARAMETERS-BOUND : bound} ::= CHOICE {
	cSFailure	[0] SEQUENCE {
			callSegmentID	[0] CallSegmentID {bound},
			reason			[1] Reason {bound}											OPTIONAL,
			cause			[2] Cause {bound}											OPTIONAL,
...
			},
	bCSMFailure	[1] SEQUENCE{
			legID			[0] LegID,
			reason			[1] Reason {bound}											OPTIONAL,
			cause			[2] Cause {bound}											OPTIONAL,
...
			}
	}

establishTemporaryConnection {PARAMETERS-BOUND : bound} OPERATION ::= {
	ARGUMENT		EstablishTemporaryConnectionArg {bound}
	RETURN RESULT	FALSE
	ERRORS 		{eTCFailed |
				missingParameter |
				systemFailure |
				taskRefused |
				unexpectedComponentSequence |
				unexpectedDataValue |
				unexpectedParameter|
				unknownLegID}
	CODE		opcode-establishTemporaryConnection
	}
-- Direction: SCF --> SSF, Timer: Tetc
-- This operation is used to create a connection to a resource for a limited period of time 
-- (e.g. to play an announcement, to collect user information); it implies the use of the assist 
-- procedure. Refer to clause 18 for a description of the procedures associated with this operation.

EstablishTemporaryConnectionArg {PARAMETERS-BOUND : bound} ::= SEQUENCE {
	assistingSSPIPRoutingAddress	[0] AssistingSSPIPRoutingAddress {bound},
	correlationID					[1] CorrelationID {bound}	OPTIONAL,
	partyToConnect					CHOICE {
			legID						[2] LegID,
			callSegmentID				[7] CallSegmentID {bound}
			}																			OPTIONAL,
	scfID							[3] ScfID {bound}									OPTIONAL,
	extensions						[4] SEQUENCE SIZE(1..bound.&numOfExtensions) OF
																ExtensionField {bound} 	OPTIONAL,
	serviceInteractionIndicators	[30] ServiceInteractionIndicators {bound}			OPTIONAL,
	serviceInteractionIndicatorsTwo	[6] ServiceInteractionIndicatorsTwo					OPTIONAL,
	...
	}

eventNotificationCharging {PARAMETERS-BOUND : bound} OPERATION ::= {
	ARGUMENT		EventNotificationChargingArg {bound}
	RETURN RESULT	FALSE
	ALWAYS RESPONDS	FALSE
	CODE			opcode-eventNotificationCharging
	}
-- Direction: SSF --> SCF, Timer: Tenc 
-- This operation is used by the SSF to report to the SCF the occurence of a specific charging event 
-- type as previously requested by the SCF in a RequestNotificationChargingEvent operation. 

EventNotificationChargingArg {PARAMETERS-BOUND : bound} ::= SEQUENCE {
	eventTypeCharging					[0] EventTypeCharging {bound},
	eventSpecificInformationCharging	[1] EventSpecificInformationCharging {bound}	OPTIONAL,
	legID								[2] LegID										OPTIONAL,
	extensions							[3] SEQUENCE SIZE(1..bound.&numOfExtensions) OF
																ExtensionField {bound} 	OPTIONAL,
	monitorMode							[30] MonitorMode				DEFAULT notifyAndContinue,
	eventTypeTariff						[50] EventTypeTariff							OPTIONAL,
	eventSpecificInformationTariff		[51] ChargingMessageType						OPTIONAL,
	...
	}
-- OPTIONAL denotes network operator specific use.

eventReportBCSM {PARAMETERS-BOUND : bound} OPERATION ::= {
	ARGUMENT		EventReportBCSMArg {bound}
	RETURN RESULT	FALSE
	ALWAYS RESPONDS	FALSE
	CODE			opcode-eventReportBCSM
	}
-- Direction: SSF --> SCF, Timer: Terb 
-- This operation is used to notify the SCF of a call-related event (e.g. BCSM events such as busy 
-- or no answer) previously requested by the SCF in a RequestReportBCSMEvent operation.

EventReportBCSMArg {PARAMETERS-BOUND : bound} ::= SEQUENCE {
	eventTypeBCSM					[0] EventTypeBCSM,
	eventSpecificInformationBCSM	[2] EventSpecificInformationBCSM {bound}			OPTIONAL,
	legID							[3] LegID											OPTIONAL,
	miscCallInfo					[4] MiscCallInfo				DEFAULT {messageType request},
	extensions						[5] SEQUENCE SIZE(1..bound.&numOfExtensions) OF 
																ExtensionField {bound} 	OPTIONAL,
	...
	}

furnishChargingInformation {PARAMETERS-BOUND : bound} OPERATION ::= {
	ARGUMENT		FurnishChargingInformationArg {bound}
	RETURN RESULT	FALSE
	ERRORS 		{missingParameter |
				taskRefused |
				unexpectedComponentSequence |
				unexpectedDataValue |
				unexpectedParameter}
	CODE		opcode-furnishChargingInformation
	}
-- Direction: SCF --> SSF, Timer: Tfci 
-- This operation is used to request the SSF to generate, register a call record or to include some 
-- information in the default call record.
-- The registered call record is intended for off line charging of the call.

FurnishChargingInformationArg {PARAMETERS-BOUND : bound} ::= FCIBillingChargingCharacteristics 
																							{bound}

initialDP {PARAMETERS-BOUND : bound} OPERATION ::= {
	ARGUMENT		InitialDPArg {bound}
	RETURN RESULT	FALSE
	ERRORS		{missingCustomerRecord |
				missingParameter |
				parameterOutOfRange |
				systemFailure |
				taskRefused |
				unexpectedComponentSequence |
				unexpectedDataValue |
				unexpectedParameter}
	CODE		opcode-initialDP
	}
-- Direction: SSF --> SCF, Timer: Tidp 
-- This operation is used after a TDP to indicate request for service.

InitialDPArg {PARAMETERS-BOUND : bound} ::= SEQUENCE {
	serviceKey							[0] ServiceKey	,
	calledPartyNumber					[2] CalledPartyNumber {bound}					OPTIONAL,
	callingPartyNumber					[3] CallingPartyNumber {bound}					OPTIONAL,
	callingPartyBusinessGroupID			[4] CallingPartyBusinessGroupID					OPTIONAL,
	callingPartysCategory				[5] CallingPartysCategory						OPTIONAL,
	cGEncountered						[7] CGEncountered								OPTIONAL,
	iPSSPCapabilities					[8] IPSSPCapabilities {bound}					OPTIONAL,
	iPAvailable							[9] IPAvailable {bound}							OPTIONAL,
	locationNumber						[10] LocationNumber {bound}						OPTIONAL,
	originalCalledPartyID				[12] OriginalCalledPartyID {bound}				OPTIONAL,
	terminalType						[14] TerminalType								OPTIONAL,
	extensions							[15] SEQUENCE SIZE(1..bound.&numOfExtensions) OF
																ExtensionField {bound}	OPTIONAL,
	highLayerCompatibility				[23] HighLayerCompatibility	OPTIONAL,
	serviceInteractionIndicators		[24] ServiceInteractionIndicators {bound}		OPTIONAL,
	additionalCallingPartyNumber		[25] AdditionalCallingPartyNumber {bound}		OPTIONAL,
	forwardCallIndicators				[26] ForwardCallIndicators						OPTIONAL,
	bearerCapability					[27] BearerCapability {bound}					OPTIONAL,
	eventTypeBCSM						[28] EventTypeBCSM								OPTIONAL,
	redirectingPartyID					[29] RedirectingPartyID {bound}					OPTIONAL,
	redirectionInformation				[30] RedirectionInformation						OPTIONAL,
	cause								[17] Cause {bound}								OPTIONAL,
	iSDNAccessRelatedInformation		[21] ISDNAccessRelatedInformation				OPTIONAL,
	iNServiceCompatibilityIndication	[22] INServiceCompatibilityIndication {bound}	OPTIONAL,
	genericNumbers						[31] GenericNumbers {bound}						OPTIONAL,
	serviceInteractionIndicatorsTwo		[32] ServiceInteractionIndicatorsTwo			OPTIONAL,
	forwardGVNS							[33] ForwardGVNS {bound}						OPTIONAL,
	createdCallSegmentAssociation		[34] CSAID {bound}								OPTIONAL,
	uSIServiceIndicator					[35] USIServiceIndicator {bound}				OPTIONAL,
	uSIInformation						[36] USIInformation {bound}						OPTIONAL,
	carrier								[37] Carrier									OPTIONAL,
	iMSI								[50] IMSI										OPTIONAL,
	subscriberState						[51] SubscriberState							OPTIONAL,
	locationInformation					[52] LocationInformation						OPTIONAL,
	ext-basicServiceCode				[53] Ext-BasicServiceCode						OPTIONAL,
	callReferenceNumber					[54] CallReferenceNumber						OPTIONAL,
	mscAddress							[55] ISDN-AddressString							OPTIONAL,
	calledPartyBCDNumber				[56] CalledPartyBCDNumber						OPTIONAL,
	...
	}
-- OPTIONAL for iPSSPCapabilities, iPAvailable, cGEncountered, and miscCallInfo denotes network 
-- operator specific use.
-- OPTIONAL for callingPartyNumber, and callingPartysCategory refer to clause 18 for the trigger 
-- detection point processing rules to specify when these parameters are included in the message.

initiateCallAttempt {PARAMETERS-BOUND : bound} OPERATION ::= {
	ARGUMENT		InitiateCallAttemptArg {bound}
	RETURN RESULT	FALSE
	ERRORS 		{missingParameter |
				parameterOutOfRange |
				systemFailure |
				taskRefused |
				unexpectedComponentSequence |
				unexpectedDataValue |
				unexpectedParameter}
	CODE		opcode-initiateCallAttempt
	}
-- Direction: SCF --> SSF, Timer: Tica 
-- This operation is used to request the SSF to create a new call to one call party using address 
-- information provided by the SCF. 

InitiateCallAttemptArg {PARAMETERS-BOUND : bound} ::= SEQUENCE {
	destinationRoutingAddress		[0] DestinationRoutingAddress {bound},
	alertingPattern					[1] AlertingPattern								OPTIONAL,
	iSDNAccessRelatedInformation	[2] ISDNAccessRelatedInformation				OPTIONAL,
	extensions						[4] SEQUENCE SIZE(1..bound.&numOfExtensions) OF
															ExtensionField {bound}	OPTIONAL,
	serviceInteractionIndicators	[29] ServiceInteractionIndicators {bound}		OPTIONAL,
	callingPartyNumber				[30] CallingPartyNumber {bound}					OPTIONAL,
	legToBeCreated					[5] LegID DEFAULT sendingSideID: leg1,
	newCallSegment					[6] CallSegmentID {bound} DEFAULT initialCallSegment,
	iNServiceCompatibilityResponse	[7] INServiceCompatibilityResponse				OPTIONAL,
	serviceInteractionIndicatorsTwo	[8] ServiceInteractionIndicatorsTwo				OPTIONAL,
	carrier							[50] Carrier {bound}							OPTIONAL,
	locationNumber					[51] LocationNumber {bound}						OPTIONAL,
	bearerCapability				[52] BearerCapability {bound}					OPTIONAL,
	...
	}

manageTriggerData {PARAMETERS-BOUND : bound} OPERATION ::= {
	ARGUMENT	ManageTriggerDataArg {bound}
	RESULT		ManageTriggerDataResultArg {bound}
	ERRORS		{missingParameter |
				missingCustomerRecord |
				parameterOutOfRange |
				systemFailure |
				taskRefused |
				unexpectedComponentSequence |
				unexpectedDataValue |
				unexpectedParameter}
	CODE		opcode-manageTriggerData 
	}
-- Direction: SCF --> SSF, Class 1, Timer: Tmtd
-- This operation is used to activate, deactivate or retrieve
-- the status of a trigger detection point linked to a subscriber profile known at the switch,
-- e.g. related to an access line.

ManageTriggerDataArg {PARAMETERS-BOUND : bound} ::= SEQUENCE {
	actionIndicator			[0] ActionIndicator,
	triggerDataIdentifier	[1] TriggerDataIdentifier {bound},
	registratorIdentifier 	[2] RegistratorIdentifier 									OPTIONAL,
	extensions				[3] SEQUENCE SIZE (1..bound.&numOfExtensions) OF
																ExtensionField {bound}	OPTIONAL,
	...
	}

ManageTriggerDataResultArg {PARAMETERS-BOUND : bound} ::= SEQUENCE {
	actionPerformed			[0] ActionPerformed,
	extensions				[1] SEQUENCE SIZE (1..bound.&numOfExtensions) OF
																ExtensionField {bound}	OPTIONAL,
	...
	}

mergeCallSegments {PARAMETERS-BOUND : bound} OPERATION ::= {
	ARGUMENT		MergeCallSegmentsArg {bound}
	RETURN RESULT TRUE
	ERRORS		{missingParameter |
				systemFailure |
				taskRefused |
				unexpectedComponentSequence |
				unexpectedDataValue |
				unexpectedParameter}
	CODE		opcode-mergeCallSegments 
	}
--	Direction: SCF --> SSF. Timer: T mc
--	This operation is issued by the SCF to merge two associated CSs with a single controlling 
--  leg into one CS with that controlling leg.
--	For additional information on this operation, refer to Q.1224.

MergeCallSegmentsArg {PARAMETERS-BOUND : bound}::= SEQUENCE {
	sourceCallSegment		[0] CallSegmentID {bound},
	targetCallSegment		[1] CallSegmentID {bound} 				DEFAULT initialCallSegment,
	extensions				[2] SEQUENCE SIZE (1..bound.&numOfExtensions) OF
																ExtensionField {bound}	OPTIONAL,
	...
	}

moveCallSegments {PARAMETERS-BOUND : bound} OPERATION ::= {
	ARGUMENT		MoveCallSegmentsArg {bound}
	RETURN RESULT TRUE
	ERRORS		{missingParameter |
				systemFailure |
				taskRefused |
				unexpectedComponentSequence |
				unexpectedDataValue |
				unexpectedParameter|
				unknownLegID}
	CODE		opcode-moveCallSegments
	}
-- Direction: SCF --> SSF, Timer Tmcs 
-- This operation moves a CS from the source CSA to the target CSA

MoveCallSegmentsArg {PARAMETERS-BOUND : bound} ::= SEQUENCE {
	targetCallSegmentAssociation	[0] CSAID {bound}, 
	callSegments					[1] SEQUENCE SIZE (1..bound.&numOfCSs) OF SEQUENCE {
		sourceCallSegment			[0] CallSegmentID {bound}	DEFAULT initialCallSegment,
		newCallSegment				[1] CallSegmentID {bound}
		},
	legs							[2] SEQUENCE SIZE (1..bound.&numOfLegs) OF SEQUENCE {
							sourceLeg	[0] LegID,
							newLeg		[1] LegID
		},
	extensions						[3] SEQUENCE SIZE (1..bound.&numOfExtensions) 
														OF ExtensionField {bound}	OPTIONAL,
	...
	}
moveLeg {PARAMETERS-BOUND : bound} OPERATION ::= {
	ARGUMENT		MoveLegArg {bound}
	RETURN RESULT TRUE
	ERRORS 		{missingParameter |
				systemFailure |
				taskRefused |
				unexpectedComponentSequence |
				unexpectedDataValue |
				unexpectedParameter|
				unknownLegID}
	CODE		opcode-moveLeg
	}
-- Direction: SCF -->SSF, Timer: T ml
-- This operation is issued by the SCF to move a leg from one CS to another with which it is 
-- associated.
MoveLegArg {PARAMETERS-BOUND : bound} ::=SEQUENCE {
	legIDToMove						[0] LegID,
	targetCallSegment				[1] CallSegmentID {bound} 						DEFAULT 1,
	extensions						[2] SEQUENCE SIZE (1..bound.&numOfExtensions) OF 
															ExtensionField {bound}	OPTIONAL,
	...
	}
-- For the OPTIONAL parameters, refer to clause 18 for the trigger 
-- detection point processing rules to specify when these parameters are 
-- included in the message.

releaseCall {PARAMETERS-BOUND : bound} OPERATION ::= {
	ARGUMENT		ReleaseCallArg {bound}
	RETURN RESULT	FALSE
	ALWAYS RESPONDS	FALSE
	CODE			opcode-releaseCall 
	}
-- Direction: SCF --> SSF, Timer: Trc 
-- This operation is used to tear down an existing call at any phase of the call for all parties 
-- involved in the call. 

ReleaseCallArg {PARAMETERS-BOUND : bound} ::= CHOICE {
	initialCallSegment	Cause {bound},
	associatedCallSegment			[1] SEQUENCE {
		callSegment						[0] INTEGER (2..bound.&numOfCSs),
		releaseCause					[1] Cause {bound} 								OPTIONAL,
		...
		},
	allCallSegments					[2] SEQUENCE {
		releaseCause					[0] Cause {bound} 								OPTIONAL,
		...
		}
	}
-- A default value of decimal 31 (normal unspecified) should be coded appropriately.

reportUTSI {PARAMETERS-BOUND : bound} OPERATION ::= {
	ARGUMENT		ReportUTSIArg {bound}
	RETURN RESULT	FALSE
	ALWAYS RESPONDS	FALSE
	CODE			opcode-reportUTSI 
	}
-- Direction: SSF --> SCF. Timer: Tru
-- This operation is issued by the SSF in the context of the USI feature. It is used to report
-- the receipt of a User to Service Information (UTSI) IE to the SCF. 

ReportUTSIArg {PARAMETERS-BOUND : bound} ::= SEQUENCE {
	uSIServiceIndicator				[0] USIServiceIndicator {bound},
	legID							[1] LegID						DEFAULT receivingSideID: leg1,
	uSIInformation					[2] USIInformation {bound},
	extensions						[3] SEQUENCE SIZE(1..bound.&numOfExtensions) OF
																ExtensionField {bound}	OPTIONAL,
	...
	}

requestNotificationChargingEvent {PARAMETERS-BOUND : bound} OPERATION ::= {
	ARGUMENT		RequestNotificationChargingEventArg {bound}
	RETURN RESULT	FALSE 
	ERRORS 		{missingParameter |
				parameterOutOfRange |
				systemFailure |
				taskRefused |
				unexpectedComponentSequence |
				unexpectedDataValue |
				unexpectedParameter | 
				unknownLegID}
	CODE		opcode-requestNotificationChargingEvent 
	}
-- Direction: SCF-->SSF, Timer: Trnc 
-- This operation is used by the SCF to instruct the SSF on how to manage the charging events
-- which are received rom other FE's and not under control of the service logic instance. 

RequestNotificationChargingEventArg {PARAMETERS-BOUND : bound} ::= SEQUENCE 
							SIZE(1..bound.&numOfChargingEvents) OF ChargingEvent {bound}

requestReportBCSMEvent {PARAMETERS-BOUND : bound} OPERATION ::= {
	ARGUMENT		RequestReportBCSMEventArg {bound}
	RETURN RESULT	FALSE
	ERRORS 			{missingParameter |
					parameterOutOfRange |
					systemFailure |
					taskRefused |
					unexpectedComponentSequence |
					unexpectedDataValue |
					unexpectedParameter | 
					unknownLegID}
	CODE			opcode-requestReportBCSMEvent 
	}
-- Direction: SCF --> SSF, Timer: Trrb
-- This operation is used to request the SSF to monitor for a call-related event
-- (e.g. BCSM events such as busy or no answer), then send a notification back to the SCF when 
-- the event is detected.
-- NOTE:
-- 		 Every EDP must be explicitly armed by the SCF via a RequestReportBCSMEvent operation. No 
--		 implicit arming of EDPs at the SSF after reception of any operation (different from 
--		 RequestReportBCSMEvent) from the SCF is allowed.

RequestReportBCSMEventArg {PARAMETERS-BOUND : bound} ::= SEQUENCE {
	bcsmEvents	[0] SEQUENCE SIZE(1..bound.&numOfBCSMEvents) OF BCSMEvent {bound},
	extensions	[2] SEQUENCE SIZE(1..bound.&numOfExtensions) OF ExtensionField {bound} 	OPTIONAL,
	...
	}
-- Indicates the BCSM related events for notification.

requestReportUTSI {PARAMETERS-BOUND : bound} OPERATION ::= {
	ARGUMENT		RequestReportUTSIArg {bound}
	RETURN RESULT	FALSE
	ERRORS 			{missingParameter |
					systemFailure |
					taskRefused |
					unexpectedComponentSequence |
					unexpectedDataValue |
					unexpectedParameter | 
					unknownLegID}
	CODE 			opcode-requestReportUTSI 
	}

-- Direction: SCF --> SSF. Timer: Trru
-- This operation is issued by the SCF in the context of the USI feature to request the SSF 
-- to monitor for a User to Service Information (UTSI) information element, which are received from
-- a user.

RequestReportUTSIArg {PARAMETERS-BOUND : bound} ::= SEQUENCE {
	requestedUTSIList	[0] RequestedUTSIList {bound},
	extensions			[1] SEQUENCE SIZE(1..bound.&numOfExtensions) OF 
																ExtensionField {bound}	OPTIONAL,
	legID				[2] LegID									DEFAULT	sendingSideID: leg1,
	...
	}

resetTimer {PARAMETERS-BOUND : bound} OPERATION ::= {
	ARGUMENT		ResetTimerArg {bound}
	RETURN RESULT	FALSE
	ERRORS 			{missingParameter |
					parameterOutOfRange |
					taskRefused |
					unexpectedComponentSequence |
					unexpectedDataValue |
					unexpectedParameter}
	CODE			opcode-resetTimer
	}
-- Direction: SCF-->SSF, Timer: Trt 
-- This operation is used to request the SSF to refresh an application timer in the SSF.

ResetTimerArg {PARAMETERS-BOUND : bound} ::= SEQUENCE {
	timerID			[0] TimerID	DEFAULT tssf,
	timervalue		[1] TimerValue,
	extensions		[2] SEQUENCE SIZE(1..bound.&numOfExtensions) OF 
																ExtensionField {bound} 	OPTIONAL,
	callSegmentID	[3] CallSegmentID {bound}											OPTIONAL,
	...
	}
sendChargingInformation {PARAMETERS-BOUND : bound} OPERATION :: = {
	ARGUMENT		SendChargingInformationArg {bound}
	RETURN RESULT	FALSE
	ERRORS 			{missingParameter |
					unexpectedComponentSequence |
					unexpectedParameter |
					parameterOutOfRange |
					systemFailure |
					taskRefused |
					unexpectedDataValue |
					unknownLegID}
	CODE			opcode-sendChargingInformation 
	}
-- Direction: SCF --> SSF, Timer: Tsci 
-- This operation is used to instruct the SSF on the charging information to send by the SSF.
-- The charging information can either be sent back by means of signalling or internal
-- if the SSF is located in the local exchange. In the local exchange
-- this information may be used to update the charge meter or to create a standard call record.

SendChargingInformationArg {PARAMETERS-BOUND : bound}::= SEQUENCE {
	sCIBillingChargingCharacteristics	[0] SCIBillingChargingCharacteristics {bound},
	partyToCharge						[1] LegID,
	extensions							[2] SEQUENCE SIZE(1..bound.&numOfExtensions) OF
															 ExtensionField {bound}		OPTIONAL,
	tariffMessage						[50] ChargingMessageType						OPTIONAL,
	...
	}

sendSTUI {PARAMETERS-BOUND : bound} OPERATION :: = {
	ARGUMENT		SendSTUIArg {bound}
	RETURN RESULT	FALSE
	ERRORS 			{missingParameter |
					parameterOutOfRange |	
					unexpectedComponentSequence |
					unexpectedParameter |
					unexpectedDataValue |
					systemFailure |
					taskRefused |
					unknownLegID}
	CODE			opcode-sendSTUI 
	}
-- Direction: SCF --> SSF. Timer: Tss
-- This operation is issued by the SCF in the context of the USI feature. It is used to request the 
-- SSF to send a Service to User Information (STUI) information element to the indicated user.

SendSTUIArg {PARAMETERS-BOUND : bound}::= SEQUENCE {
	uSIServiceIndicator	[0] USIServiceIndicator {bound},
	legID				[1] LegID	DEFAULT sendingSideID: leg1,
	uSIInformation		[2] USIInformation {bound},
	extensions			[3] SEQUENCE SIZE(1..bound.&numOfExtensions) OF
																ExtensionField {bound}	OPTIONAL,
	...
	}

serviceFilteringResponse {PARAMETERS-BOUND : bound} OPERATION :: = {
	ARGUMENT		ServiceFilteringResponseArg {bound}
	RETURN RESULT	FALSE
	ALWAYS RESPONDS	FALSE
	CODE			opcode-serviceFilteringResponse 
	} 
-- Direction: SSF-->SCF, Timer: Tsfr 
-- This operation is used to send back to the SCF the values of counters specified in a previous 
-- ActivateServiceFiltering operation

ServiceFilteringResponseArg {PARAMETERS-BOUND : bound}::= SEQUENCE {
	countersValue		[0] CountersValue,
	filteringCriteria	[1] FilteringCriteria {bound},
	extensions			[2] SEQUENCE SIZE(1..bound.&numOfExtensions) OF
															 ExtensionField {bound}		OPTIONAL,
	responseCondition	[3] ResponseCondition											OPTIONAL,
	...
	}

splitLeg {PARAMETERS-BOUND : bound} OPERATION :: = {
	ARGUMENT	SplitLegArg {bound}
	RETURN RESULT TRUE
	ERRORS 	{missingParameter |
			unexpectedComponentSequence |
			unexpectedParameter |
			unexpectedDataValue |
			systemFailure |
			taskRefused |
			unknownLegID
			}
	CODE	opcode-splitLeg 
	}
-- Direction: SCF --> SSF. Timer: T sl
-- This operation is issued by the SCF to separate one joined leg from a multi-way connection
-- or to interrupt the bearer connection between the involved legs of a single 2 party Call segment.

SplitLegArg {PARAMETERS-BOUND : bound}::= SEQUENCE {
	legToBeSplit	[0] LegID,
	newCallSegment	[1] INTEGER (2..bound.&numOfCSs),
	extensions		[2] SEQUENCE SIZE (1..bound.&numOfExtensions) OF ExtensionField {bound}
																						OPTIONAL,
	...
	}

END

IN-CS2-SSF-SCF-pkgs-contracts-acs {ccitt(0) identified-organization(4) etsi(0) inDomain(1) in-network(1) CS2(20) modules(0) in-cs2-ssf-scf-pkgs-contracts-acs (6) version1(0)}
DEFINITIONS ::=
BEGIN

-- This module describes the operation-packages, contracts and application-contexts used
-- over the SSF-SCF interface.

IMPORTS

	PARAMETERS-BOUND,
	networkSpecificBoundSet
FROM IN-CS2-classes classes 


	ROS-OBJECT-CLASS, CONTRACT, OPERATION-PACKAGE, OPERATION
FROM Remote-Operations-Information-Objects ros-InformationObjects

	TCMessage {} 
FROM TCAPMessages tc-Messages

	APPLICATION-CONTEXT, dialogue-abstract-syntax
FROM TC-Notation-Extensions tc-NotationExtensions

		activateServiceFiltering {},
		activityTest,
		applyCharging {},
		applyChargingReport {},
		assistRequestInstructions {},
		callGap {},
		callInformationReport {},
		callInformationRequest {},
		cancel {},
		collectInformation {},
		connect {},
		connectToResource {},
		continue,
		continueWithArgument {},
		createCallSegmentAssociation {},
		disconnectForwardConnection,
		disconnectForwardConnectionWithArgument {}, 
		disconnectLeg {},
		entityReleased {},
		establishTemporaryConnection {},
		eventNotificationCharging {},
		eventReportBCSM {},
		furnishChargingInformation {},
		initialDP {},
		initiateCallAttempt {},
		manageTriggerData {},
		mergeCallSegments {},
		moveCallSegments {},
		moveLeg {},
		releaseCall {},
		reportUTSI {},
		requestNotificationChargingEvent {},
		requestReportBCSMEvent {},
		requestReportUTSI {},
		resetTimer {},
		sendChargingInformation {},
		sendSTUI {},
		serviceFilteringResponse {},
		splitLeg {}
FROM IN-CS2-SSF-SCF-ops-args ssf-scf-Operations

		playAnnouncement {},
		promptAndCollectUserInformation {},
		promptAndReceiveMessage {},
		scriptClose {},
		scriptEvent {},
		scriptInformation {},
		scriptRun {},
		specializedResourceReport
FROM IN-CS2-SCF-SRF-ops-args scf-srf-Operations

	specializedResourceControlPackage {},
	scriptControlPackage {},
	messageControlPackage {}
FROM IN-CS2-SCF-SRF-pkgs-contracts-acs scf-srf-Protocol

	id-ac-cs2-ssf-scfGenericAC,
	id-ac-cs2-ssf-scfAssistHandoffAC,
	id-ac-cs2-ssf-scfServiceManagementAC,
	id-ac-cs2-scf-ssfGenericAC,
	id-ac-cs2-scf-ssfTrafficManagementAC,
	id-ac-cs2-scf-ssfServiceManagementAC,
	id-ac-cs2-scf-ssfTriggerManagementAC,
	id-inCs2SsfToScfGeneric,
	id-inCs2AssistHandoffssfToScf,
	id-inCs2ScfToSsfGeneric,
	id-inCs2ScfToSsfTrafficManagement,
	id-inCs2ScfToSsfServiceManagement,
	id-inCs2SsfToScfServiceManagement,
	id-inCs2ScfToSsfTriggerManagement,
	id-as-ssf-scfGenericAS,
	id-as-assistHandoff-ssf-scfAS,
	id-as-scf-ssfGenericAS,
	id-as-scf-ssfTrafficManagementAS,
	id-as-scf-ssfServiceManagementAS,
	id-as-ssf-scfServiceManagementAS,
	id-as-scf-ssfTriggerManagementAS,
	id-package-scfActivation,
	id-package-srf-scfActivationOfAssist,
	id-package-assistConnectionEstablishment,
	id-package-genericDisconnectResource,
	id-package-nonAssistedConnectionEstablishment,
	id-package-connect,
	id-package-callHandling,
	id-package-bcsmEventHandling,
	id-package-chargingEventHandling,
	id-package-ssfCallProcessing,
	id-package-scfCallInitiation,
	id-package-timer,
	id-package-billing,
	id-package-charging,
	id-package-trafficManagement,
	id-package-serviceManagementActivate,
	id-package-serviceManagementResponse,
	id-package-callReport,
	id-package-signallingControl,
	id-package-activityTest,
	id-package-cancel,
	id-package-cphResponse,
	id-package-entityReleased,
	id-package-triggerManagement,
	id-package-uSIHandling,
	classes, ros-InformationObjects, tc-Messages, tc-NotationExtensions, 
	ssf-scf-Operations, scf-srf-Operations, scf-srf-Protocol
FROM IN-CS2-object-identifiers {ccitt(0) identified-organization(4) etsi(0) inDomain(1) in-network(1) CS2(20) modules(0) in-cs2-object-identifiers (17) version1(0)}

;
-- Application Contexts

cs2ssf-scfGenericAC APPLICATION-CONTEXT ::= {
	CONTRACT					inCs2SsfToScfGeneric
	DIALOGUE MODE				structured
	ABSTRACT SYNTAXES			{dialogue-abstract-syntax |
								ssf-scfGenericAbstractSyntax} 
	APPLICATION CONTEXT NAME	id-ac-cs2-ssf-scfGenericAC}

cs2ssf-scfAssistHandoffAC APPLICATION-CONTEXT ::= 	{
	CONTRACT					inCs2AssistHandoffssfToScf
	DIALOGUE MODE				structured
	ABSTRACT SYNTAXES			{dialogue-abstract-syntax |
								assistHandoff-ssf-scfAbstractSyntax}
	APPLICATION CONTEXT NAME	id-ac-cs2-ssf-scfAssistHandoffAC}

cs2ssf-scfServiceManagementAC APPLICATION-CONTEXT ::= {
	CONTRACT					inCs2SsfToScfServiceManagement
	DIALOGUE MODE				structured
	ABSTRACT SYNTAXES			{dialogue-abstract-syntax |
								ssf-scfServiceManagementAbstractSyntax} 
	APPLICATION CONTEXT NAME	id-ac-cs2-ssf-scfServiceManagementAC}

cs2scf-ssfGenericAC APPLICATION-CONTEXT ::= {
	CONTRACT					inCs2ScfToSsfGeneric
	DIALOGUE MODE				structured
	ABSTRACT SYNTAXES			{dialogue-abstract-syntax |
								ssf-scfGenericAbstractSyntax}
	APPLICATION CONTEXT NAME	id-ac-cs2-scf-ssfGenericAC}

cs2scf-ssfTrafficManagementAC APPLICATION-CONTEXT ::= {
	CONTRACT					inCs2ScfToSsfTrafficManagement
	DIALOGUE MODE				structured
	ABSTRACT SYNTAXES			{dialogue-abstract-syntax |
								scf-ssfTrafficManagementAbstractSyntax} 
	APPLICATION CONTEXT NAME	id-ac-cs2-scf-ssfTrafficManagementAC}

cs2scf-ssfServiceManagementAC APPLICATION-CONTEXT ::= {
	CONTRACT					inCs2ScfToSsfServiceManagement
	DIALOGUE MODE				structured
	ABSTRACT SYNTAXES			{dialogue-abstract-syntax |
								scf-ssfServiceManagementAbstractSyntax}
	APPLICATION CONTEXT NAME	id-ac-cs2-scf-ssfServiceManagementAC}

cs2scf-ssfTriggerManagementAC APPLICATION-CONTEXT ::= {
	CONTRACT					inCs2ScfToSsfTriggerManagement
	DIALOGUE MODE				structured
	ABSTRACT SYNTAXES			{dialogue-abstract-syntax |
								scf-ssfTriggerManagementAbstractSyntax} 
	APPLICATION CONTEXT NAME	id-ac-cs2-scf-ssfTriggerManagementAC}


-- Contracts

inCs2SsfToScfGeneric CONTRACT ::= {
-- dialogue initiated by SSF with InitialDP Operation
	INITIATOR CONSUMER OF	
			{exceptionInformPackage {networkSpecificBoundSet} |
			scfActivationPackage {networkSpecificBoundSet}}
	RESPONDER CONSUMER OF
			{activityTestPackage|
			assistConnectionEstablishmentPackage {networkSpecificBoundSet} |
			bcsmEventHandlingPackage {networkSpecificBoundSet} |
			billingPackage {networkSpecificBoundSet} |
			callHandlingPackage {networkSpecificBoundSet} |
			callReportPackage {networkSpecificBoundSet} |
			cancelPackage {networkSpecificBoundSet} |
			chargingEventHandlingPackage {networkSpecificBoundSet} |
			chargingPackage {networkSpecificBoundSet} |
			connectPackage {networkSpecificBoundSet} |
			cphResponsePackage {networkSpecificBoundSet} |
			genericDisconnectResourcePackage {networkSpecificBoundSet} |
			nonAssistedConnectionEstablishmentPackage {networkSpecificBoundSet} |
			scfCallInitiationPackage {networkSpecificBoundSet} |
			signallingControlPackage {networkSpecificBoundSet} |
			specializedResourceControlPackage {networkSpecificBoundSet} |
			scriptControlPackage {networkSpecificBoundSet} |
			messageControlPackage {networkSpecificBoundSet} |
			ssfCallProcessingPackage {networkSpecificBoundSet} |
			timerPackage {networkSpecificBoundSet} |
			trafficManagementPackage {networkSpecificBoundSet} |
			uSIHandlingPackage {networkSpecificBoundSet}
			}
	ID		id-inCs2SsfToScfGeneric
	}

inCs2AssistHandoffssfToScf CONTRACT :: = {
-- dialogue initiated by SSF with AssistRequestInstructions
	INITIATOR CONSUMER OF
			{srf-scfActivationOfAssistPackage {networkSpecificBoundSet}}
	RESPONDER CONSUMER OF
			{activityTestPackage|
			billingPackage {networkSpecificBoundSet} |
			callHandlingPackage {networkSpecificBoundSet} |
			cancelPackage {networkSpecificBoundSet} |
			chargingPackage {networkSpecificBoundSet} |
			genericDisconnectResourcePackage {networkSpecificBoundSet} |
			nonAssistedConnectionEstablishmentPackage {networkSpecificBoundSet} |
			specializedResourceControlPackage {networkSpecificBoundSet} |
			scriptControlPackage {networkSpecificBoundSet} |
			messageControlPackage {networkSpecificBoundSet} |
			timerPackage {networkSpecificBoundSet}
			}
	ID		id-inCs2AssistHandoffssfToScf
	}

inCs2ScfToSsfGeneric CONTRACT :: = {
-- dialogue initiated by SCF with InitiateCallAttempt or CreateCallSegmentAssociation, Generic Case
	INITIATOR CONSUMER OF
			{activityTestPackage|
			assistConnectionEstablishmentPackage {networkSpecificBoundSet} |
			bcsmEventHandlingPackage {networkSpecificBoundSet} |
			billingPackage {networkSpecificBoundSet} |
			callHandlingPackage {networkSpecificBoundSet} |
			callReportPackage {networkSpecificBoundSet} |
			cancelPackage {networkSpecificBoundSet} |
			chargingEventHandlingPackage {networkSpecificBoundSet} |
			chargingPackage {networkSpecificBoundSet} |
			connectPackage {networkSpecificBoundSet} |
			cphResponsePackage {networkSpecificBoundSet} |
			genericDisconnectResourcePackage {networkSpecificBoundSet} |
			nonAssistedConnectionEstablishmentPackage {networkSpecificBoundSet} |
			scfCallInitiationPackage {networkSpecificBoundSet} |
			signallingControlPackage {networkSpecificBoundSet} |
			specializedResourceControlPackage {networkSpecificBoundSet} |
			scriptControlPackage {networkSpecificBoundSet} |
			messageControlPackage {networkSpecificBoundSet} |
			ssfCallProcessingPackage {networkSpecificBoundSet} |
			timerPackage {networkSpecificBoundSet} |
			uSIHandlingPackage {networkSpecificBoundSet}
			}
	RESPONDER CONSUMER OF
			{exceptionInformPackage {networkSpecificBoundSet}}
	ID		id-inCs2ScfToSsfGeneric
	}

inCs2ScfToSsfTrafficManagement CONTRACT :: = {
-- dialogue initiated by SCF with CallGap
	INITIATOR CONSUMER OF
			{trafficManagementPackage {networkSpecificBoundSet}
			}
	ID		id-inCs2ScfToSsfTrafficManagement
	}

inCs2ScfToSsfServiceManagement CONTRACT :: = {
-- dialogue initiated by SCF with ActivateServiceFiltering
	INITIATOR CONSUMER OF
			{serviceManagementActivatePackage {networkSpecificBoundSet}
			}
	ID		id-inCs2ScfToSsfServiceManagement
	}

inCs2SsfToScfServiceManagement CONTRACT :: = {
-- dialogue initiated/ended by SSF with ServiceFilteringResponse
	INITIATOR CONSUMER OF
			{serviceManagementResponsePackage {networkSpecificBoundSet}
			}
	ID		id-inCs2SsfToScfServiceManagement
	}

inCs2ScfToSsfTriggerManagement CONTRACT :: = {
-- dialogue initiated by SCF with Manage Trigger Data
	INITIATOR CONSUMER OF	{triggerManagementPackage {networkSpecificBoundSet}
			}
	ID		id-inCs2ScfToSsfTriggerManagement
	}

-- Operation Packages

scfActivationPackage {PARAMETERS-BOUND : bound} OPERATION-PACKAGE :: = {
	CONSUMER INVOKES	{initialDP {bound}}
	ID		id-package-scfActivation}
srf-scfActivationOfAssistPackage {PARAMETERS-BOUND : bound} OPERATION-PACKAGE :: = {
	CONSUMER INVOKES	{assistRequestInstructions {bound}}
	ID		id-package-srf-scfActivationOfAssist}
assistConnectionEstablishmentPackage {PARAMETERS-BOUND : bound}  OPERATION-PACKAGE :: = {
	CONSUMER INVOKES	{establishTemporaryConnection {bound}}
	ID		id-package-assistConnectionEstablishment}
genericDisconnectResourcePackage {PARAMETERS-BOUND : bound} OPERATION-PACKAGE :: = {
	CONSUMER INVOKES	{disconnectForwardConnection |
			disconnectForwardConnectionWithArgument {bound}}
	ID		id-package-genericDisconnectResource}
nonAssistedConnectionEstablishmentPackage {PARAMETERS-BOUND : bound} OPERATION-PACKAGE :: = {
	CONSUMER INVOKES	{connectToResource {bound}}
	ID		id-package-nonAssistedConnectionEstablishment}
connectPackage {PARAMETERS-BOUND : bound} OPERATION-PACKAGE :: = {
	CONSUMER INVOKES	{connect {bound}}
	ID		id-package-connect}
callHandlingPackage {PARAMETERS-BOUND : bound} OPERATION-PACKAGE :: = {
	CONSUMER INVOKES	{releaseCall {bound}}
	ID		id-package-callHandling}
bcsmEventHandlingPackage {PARAMETERS-BOUND : bound} OPERATION-PACKAGE :: = {
	CONSUMER INVOKES	{requestReportBCSMEvent {bound}}
	SUPPLIER INVOKES	{eventReportBCSM {bound}}
	ID		id-package-bcsmEventHandling}
chargingEventHandlingPackage {PARAMETERS-BOUND : bound} OPERATION-PACKAGE :: = {
	CONSUMER INVOKES	{requestNotificationChargingEvent {bound}}
	SUPPLIER INVOKES	{eventNotificationCharging {bound}}
	ID		id-package-chargingEventHandling}
ssfCallProcessingPackage {PARAMETERS-BOUND : bound} OPERATION-PACKAGE :: = {
	CONSUMER INVOKES	{collectInformation {bound} | continue}
	ID		id-package-ssfCallProcessing}
scfCallInitiationPackage {PARAMETERS-BOUND : bound} OPERATION-PACKAGE :: = {
	CONSUMER INVOKES	{initiateCallAttempt {bound}}
	ID		id-package-scfCallInitiation}
timerPackage {PARAMETERS-BOUND : bound} OPERATION-PACKAGE :: = {
	CONSUMER INVOKES	{resetTimer {bound}}
	ID		id-package-timer}
billingPackage {PARAMETERS-BOUND : bound} OPERATION-PACKAGE :: = {
	CONSUMER INVOKES	{furnishChargingInformation {bound}}
	ID		id-package-billing}
chargingPackage {PARAMETERS-BOUND : bound} OPERATION-PACKAGE :: = {
	CONSUMER INVOKES	{applyCharging {bound}}
	SUPPLIER INVOKES	{applyChargingReport {bound}}
	ID		id-package-charging}
trafficManagementPackage {PARAMETERS-BOUND : bound} OPERATION-PACKAGE :: = {
	CONSUMER INVOKES	{callGap {bound}}
	ID		id-package-trafficManagement}
serviceManagementActivatePackage {PARAMETERS-BOUND : bound} OPERATION-PACKAGE :: = {
	CONSUMER INVOKES	{activateServiceFiltering {bound}}
	ID		id-package-serviceManagementActivate}
serviceManagementResponsePackage {PARAMETERS-BOUND : bound} OPERATION-PACKAGE :: = {
	CONSUMER INVOKES	{serviceFilteringResponse {bound}}
	ID		id-package-serviceManagementResponse}
callReportPackage {PARAMETERS-BOUND : bound} OPERATION-PACKAGE :: = {
	CONSUMER INVOKES	{callInformationRequest {bound}}
	SUPPLIER INVOKES	{callInformationReport {bound}}
	ID		id-package-callReport}
signallingControlPackage {PARAMETERS-BOUND : bound} OPERATION-PACKAGE :: = {
	CONSUMER INVOKES	{sendChargingInformation {bound}}
	ID		id-package-signallingControl}
activityTestPackage OPERATION-PACKAGE :: = {
	CONSUMER INVOKES	{activityTest}
	ID		id-package-activityTest}
cancelPackage {PARAMETERS-BOUND : bound} OPERATION-PACKAGE :: = {
	CONSUMER INVOKES	{cancel {bound}}
	ID		id-package-cancel}
cphResponsePackage {PARAMETERS-BOUND : bound} OPERATION-PACKAGE :: = {
	CONSUMER INVOKES	{
			continueWithArgument {bound}| 
			disconnectLeg {bound}| 
			mergeCallSegments {bound}|
			moveCallSegments {bound}|
			moveLeg {bound}| 
			createCallSegmentAssociation {bound} |
			splitLeg {bound} 
			}
	ID		id-package-cphResponse}
exceptionInformPackage {PARAMETERS-BOUND : bound} OPERATION-PACKAGE :: = {
	CONSUMER INVOKES	{entityReleased {bound}}
	ID		id-package-entityReleased}
triggerManagementPackage {PARAMETERS-BOUND : bound} OPERATION-PACKAGE :: = {
	CONSUMER INVOKES	{manageTriggerData {bound}}
	ID		id-package-triggerManagement}
uSIHandlingPackage {PARAMETERS-BOUND : bound} OPERATION-PACKAGE :: = {
	CONSUMER INVOKES	{requestReportUTSI {bound}| sendSTUI {bound}}
	SUPPLIER INVOKES	{reportUTSI {bound}}
	ID		id-package-uSIHandling
	}



-- Abstract Syntaxes

ssf-scfGenericAbstractSyntax ABSTRACT-SYNTAX :: = {
	GenericSSF-SCF-PDUs
	IDENTIFIED BY	id-as-ssf-scfGenericAS}
GenericSSF-SCF-PDUs :: = TCMessage {{SsfToScfGenericInvokable}, 
			{SsfToScfGenericReturnable}}
SsfScfGenericInvokable OPERATION :: = {
			activityTest |
			applyCharging {networkSpecificBoundSet} |
			applyChargingReport {networkSpecificBoundSet} |
			callInformationReport {networkSpecificBoundSet} |
			callInformationRequest {networkSpecificBoundSet} |
			cancel {networkSpecificBoundSet} |
			collectInformation {networkSpecificBoundSet} |
			connect {networkSpecificBoundSet} |
			connectToResource {networkSpecificBoundSet} |
			disconnectForwardConnection |
			disconnectForwardConnectionWithArgument {networkSpecificBoundSet}|
			disconnectLeg {networkSpecificBoundSet} |
			entityReleased {networkSpecificBoundSet} |
			establishTemporaryConnection {networkSpecificBoundSet} | 
			eventNotificationCharging {networkSpecificBoundSet} |
			eventReportBCSM {networkSpecificBoundSet} |
			furnishChargingInformation {networkSpecificBoundSet} |
			initialDP {networkSpecificBoundSet} |
			mergeCallSegments {networkSpecificBoundSet} |
			moveCallSegments {networkSpecificBoundSet} |
			moveLeg {networkSpecificBoundSet} |
			createCallSegmentAssociation {networkSpecificBoundSet} |
			releaseCall {networkSpecificBoundSet} |
			reportUTSI {networkSpecificBoundSet} |
			requestNotificationChargingEvent {networkSpecificBoundSet} |
			requestReportBCSMEvent {networkSpecificBoundSet} |
			requestReportUTSI {networkSpecificBoundSet} |
			resetTimer {networkSpecificBoundSet} |
			sendChargingInformation {networkSpecificBoundSet} |
			sendSTUI {networkSpecificBoundSet} |
			splitLeg {networkSpecificBoundSet} |
			playAnnouncement {networkSpecificBoundSet} |
			promptAndCollectUserInformation {networkSpecificBoundSet} |
			scriptClose {networkSpecificBoundSet} |
			scriptEvent {networkSpecificBoundSet} |
			scriptInformation {networkSpecificBoundSet} |
			scriptRun {networkSpecificBoundSet} |
			specializedResourceReport |
			promptAndReceiveMessage {networkSpecificBoundSet}
			}
SsfScfGenericReturnable OPERATION :: = {
			activityTest | 
			applyCharging {networkSpecificBoundSet} | 
			applyChargingReport {networkSpecificBoundSet} | 
			callGap {networkSpecificBoundSet} |
			callInformationRequest {networkSpecificBoundSet} | 
			cancel {networkSpecificBoundSet} | 
			collectInformation {networkSpecificBoundSet} | 
			connect {networkSpecificBoundSet} | 
			connectToResource {networkSpecificBoundSet} | 
			continue | 
			continueWithArgument {networkSpecificBoundSet}|
			disconnectForwardConnection | 
			disconnectForwardConnectionWithArgument {networkSpecificBoundSet}|
			disconnectLeg {networkSpecificBoundSet}|
			establishTemporaryConnection {networkSpecificBoundSet}| 
			furnishChargingInformation {networkSpecificBoundSet}| 
			initialDP {networkSpecificBoundSet}|
			mergeCallSegments {networkSpecificBoundSet}|
			moveCallSegments {networkSpecificBoundSet}|
			moveLeg {networkSpecificBoundSet}|
			createCallSegmentAssociation {networkSpecificBoundSet}|
			releaseCall {networkSpecificBoundSet}| 
			requestNotificationChargingEvent {networkSpecificBoundSet}| 
			requestReportBCSMEvent {networkSpecificBoundSet}|
			requestReportUTSI {networkSpecificBoundSet}|
			resetTimer {networkSpecificBoundSet}| 
			sendChargingInformation {networkSpecificBoundSet}|
			sendSTUI {networkSpecificBoundSet}|
			splitLeg {networkSpecificBoundSet}|
			playAnnouncement {networkSpecificBoundSet}|
			promptAndCollectUserInformation {networkSpecificBoundSet}|
			scriptClose {networkSpecificBoundSet}|
			scriptInformation {networkSpecificBoundSet}|
			scriptRun {networkSpecificBoundSet}|
			promptAndReceiveMessage {networkSpecificBoundSet}
			}

assistHandoff-ssf-scfAbstractSyntax ABSTRACT-SYNTAX :: = {
	AssistHandoffsSF-SCF-PDUs
	IDENTIFIED BY	id-as-assistHandoff-ssf-scfAS}
AssistHandoffsSF-SCF-PDUs :: = TCMessage {{AssistHandoffssfToScfInvokable}, 
			{AssistHandoffssfToScfReturnable}}
AssistHandoffssfToScfInvokable OPERATION :: = {
			activityTest |
			applyCharging {networkSpecificBoundSet}| 
			applyChargingReport {networkSpecificBoundSet}| 
			assistRequestInstructions {networkSpecificBoundSet}| 
			cancel {networkSpecificBoundSet}| 
			connectToResource {networkSpecificBoundSet}| 
			disconnectForwardConnection | 
			disconnectForwardConnectionWithArgument {networkSpecificBoundSet}|
			furnishChargingInformation {networkSpecificBoundSet}| 
			playAnnouncement {networkSpecificBoundSet}| 
			promptAndCollectUserInformation {networkSpecificBoundSet}| 
			resetTimer {networkSpecificBoundSet}| 
			scriptClose {networkSpecificBoundSet}|
			scriptEvent {networkSpecificBoundSet}|
			scriptInformation {networkSpecificBoundSet}|
			scriptRun {networkSpecificBoundSet}|
			specializedResourceReport |
			promptAndReceiveMessage {networkSpecificBoundSet}
			}
AssistHandoffssfToScfReturnable OPERATION :: = {
			activityTest |
			applyCharging {networkSpecificBoundSet}| 
			applyChargingReport {networkSpecificBoundSet}| 
			assistRequestInstructions {networkSpecificBoundSet}| 
			cancel {networkSpecificBoundSet}| 
			connectToResource {networkSpecificBoundSet}| 
			disconnectForwardConnection | 
			disconnectForwardConnectionWithArgument {networkSpecificBoundSet}|
			furnishChargingInformation {networkSpecificBoundSet}| 
			playAnnouncement {networkSpecificBoundSet}| 
			promptAndCollectUserInformation {networkSpecificBoundSet}| 
			resetTimer {networkSpecificBoundSet}|
			scriptClose {networkSpecificBoundSet}|
			scriptInformation {networkSpecificBoundSet}|
			scriptRun {networkSpecificBoundSet}|
			promptAndReceiveMessage {networkSpecificBoundSet}
			}


scf-ssfGenericAbstractSyntax ABSTRACT-SYNTAX :: = {
	GenericSCF-SSF-PDUs
	IDENTIFIED BY	id-as-scf-ssfGenericAS}
GenericSCF-SSF-PDUs :: = TCMessage {{ScfToSsfGenericInvokable}, {ScfToSsfGenericReturnable}}
ScfSsfGenericInvokable OPERATION :: = {
			activityTest | 
			applyCharging {networkSpecificBoundSet}| 
			applyChargingReport {networkSpecificBoundSet}| 
			callInformationRequest {networkSpecificBoundSet}| 
			cancel {networkSpecificBoundSet}| 
			collectInformation {networkSpecificBoundSet}| 
			connect {networkSpecificBoundSet}| 
			connectToResource {networkSpecificBoundSet}| 
			continue | 
			continueWithArgument{networkSpecificBoundSet}|
			disconnectForwardConnection | 
			disconnectForwardConnectionWithArgument {networkSpecificBoundSet}|
			disconnectLeg {networkSpecificBoundSet}|
			establishTemporaryConnection {networkSpecificBoundSet}| 
			furnishChargingInformation {networkSpecificBoundSet}| 
			initiateCallAttempt {networkSpecificBoundSet}|
			mergeCallSegments {networkSpecificBoundSet}|
			moveCallSegments {networkSpecificBoundSet}|
			moveLeg {networkSpecificBoundSet}|
			createCallSegmentAssociation {networkSpecificBoundSet}|
			releaseCall {networkSpecificBoundSet}| 
			requestNotificationChargingEvent {networkSpecificBoundSet}| 
			requestReportBCSMEvent {networkSpecificBoundSet}|
			requestReportUTSI {networkSpecificBoundSet}|
			resetTimer {networkSpecificBoundSet}| 
			sendChargingInformation {networkSpecificBoundSet}| 
			sendSTUI {networkSpecificBoundSet}|
			splitLeg {networkSpecificBoundSet}|
			playAnnouncement {networkSpecificBoundSet}|
			promptAndCollectUserInformation {networkSpecificBoundSet}|
			scriptClose {networkSpecificBoundSet}|
			scriptInformation {networkSpecificBoundSet}|
			scriptRun {networkSpecificBoundSet}|
			promptAndReceiveMessage {networkSpecificBoundSet}
			}
ScfSsfGenericReturnable OPERATION :: = {
			activityTest | 
			applyCharging {networkSpecificBoundSet}| 
			applyChargingReport {networkSpecificBoundSet}|
			callInformationReport {networkSpecificBoundSet}| 
			callInformationRequest {networkSpecificBoundSet}| 
			cancel {networkSpecificBoundSet}| 
			collectInformation {networkSpecificBoundSet}| 
			connect {networkSpecificBoundSet}| 
			connectToResource {networkSpecificBoundSet}| 
			disconnectForwardConnection | 
			disconnectForwardConnectionWithArgument {networkSpecificBoundSet}|
			disconnectLeg {networkSpecificBoundSet}|
			entityReleased {networkSpecificBoundSet}|
			establishTemporaryConnection {networkSpecificBoundSet}| 
			eventNotificationCharging {networkSpecificBoundSet} | 
			resetTimer {networkSpecificBoundSet}| 
			eventReportBCSM {networkSpecificBoundSet}| 
			furnishChargingInformation {networkSpecificBoundSet}| 
			initiateCallAttempt {networkSpecificBoundSet}| 
			mergeCallSegments {networkSpecificBoundSet}|
			moveCallSegments {networkSpecificBoundSet}|
			moveLeg {networkSpecificBoundSet}|
			createCallSegmentAssociation {networkSpecificBoundSet}|
			reportUTSI {networkSpecificBoundSet}|
			requestNotificationChargingEvent {networkSpecificBoundSet}| 
			requestReportBCSMEvent {networkSpecificBoundSet}| 
			requestReportUTSI {networkSpecificBoundSet} |
			sendChargingInformation {networkSpecificBoundSet}| 
			sendSTUI {networkSpecificBoundSet}|
			splitLeg {networkSpecificBoundSet}|
			playAnnouncement {networkSpecificBoundSet}|
			promptAndCollectUserInformation {networkSpecificBoundSet}|
			scriptClose {networkSpecificBoundSet}|
			scriptEvent {networkSpecificBoundSet}|
			scriptInformation {networkSpecificBoundSet}|
			scriptRun {networkSpecificBoundSet}|
			specializedResourceReport |
			promptAndReceiveMessage {networkSpecificBoundSet}
			}


scf-ssfTrafficManagementAbstractSyntax ABSTRACT-SYNTAX :: = {
	TrafficManagementSCF-SSF-PDUs
	IDENTIFIED BY	id-as-scf-ssfTrafficManagementAS}
TrafficManagementSCF-SSF-PDUs :: = TCMessage {{ScfToSsfTrafficManagementInvokable}} 
ScfToSsfTrafficManagementInvokable OPERATION :: = {
	callGap {networkSpecificBoundSet}
	}

scf-ssfServiceManagementAbstractSyntax ABSTRACT-SYNTAX :: = {
	ServiceManagementSCF-SSF-PDUs
	IDENTIFIED BY	id-as-scf-ssfServiceManagementAS}
ServiceManagementSCF-SSF-PDUs :: = TCMessage {{ScfToSsfServiceManagementInvokable}, 
			{ScfToSsfServiceManagementReturnable}}
ScfToSsfServiceManagementInvokable OPERATION :: = {
	activateServiceFiltering {networkSpecificBoundSet}
	}
ScfToSsfServiceManagementReturnable OPERATION :: = {
	activateServiceFiltering {networkSpecificBoundSet}
	}

ssf-scfServiceManagementAbstractSyntax ABSTRACT-SYNTAX :: = {
	ServiceManagementSSF-SCF-PDUs
	IDENTIFIED BY	id-as-ssf-scfServiceManagementAS}
ServiceManagementSSF-SCF-PDUs :: = TCMessage {{SsfToScfServiceManagementInvokable}}
SsfToScfServiceManagementInvokable OPERATION :: = {
	serviceFilteringResponse {networkSpecificBoundSet}
	}

scf-ssfTriggerManagementAbstractSyntax ABSTRACT-SYNTAX :: = {
	TriggerManagementSCF-SSF-PDUs
	IDENTIFIED BY	id-as-scf-ssfTriggerManagementAS}
TriggerManagementSCF-SSF-PDUs :: = TCMessage {{ScfToSsfTriggerManagementInvokable}, 
			{ScfToSsfTriggerManagementReturnable}}
ScfToSsfTriggerManagementInvokable OPERATION :: = {
	manageTriggerData {networkSpecificBoundSet}
	}
ScfToSsfTriggerManagementReturnable OPERATION :: = {
	manageTriggerData {networkSpecificBoundSet}
	}

END


IN-CS2-SCF-SRF-ops-args {ccitt recommendation q 1228 modules(0) in-cs2-scf-srf-ops-args (7) version1(0)}

DEFINITIONS IMPLICIT TAGS ::=

BEGIN

IMPORTS

	OPERATION
FROM Remote-Operations-Information-Objects ros-InformationObjects

	opcode-playAnnouncement,
	opcode-promptAndCollectUserInformation,
	opcode-promptAndReceiveMessage,
	opcode-scriptClose,
	opcode-scriptEvent,
	opcode-scriptInformation,
	opcode-scriptRun,
	opcode-specializedResourceReport
FROM IN-CS2-operationcodes operationcodes

	CallSegmentID {},
	CollectedInfo,
	Digits {},
	ExtensionField {},
	InformationToRecord {},
	InformationToSend {},
	LegID,
	MailBoxID {},
	Media,
	GenericNumber {},
	ReceivedStatus,
	RecordedMessageID
FROM IN-CS2-datatypes datatypes

	canceled,
	improperCallerResponse,
	missingParameter,
	parameterOutOfRange,
	systemFailure,
	taskRefused,
	unavailableResource,
	unexpectedComponentSequence,
	unexpectedDataValue,
	unexpectedParameter,
	unknownSubscriber
FROM IN-CS2-errortypes errortypes

	UISCRIPT,
	SupportedUIScripts {},
	PARAMETERS-BOUND
FROM IN-CS2-classes classes

	ros-InformationObjects, operationcodes, datatypes, errortypes, classes
FROM IN-CS2-object-identifiers 	
{ccitt recommendation q 1228 modules(0) in-cs2-object-identifiers(17) version1(0)}
;

playAnnouncement {PARAMETERS-BOUND : bound} OPERATION :: = {
	ARGUMENT		PlayAnnouncementArg {bound}
	RETURN RESULT	FALSE
	ERRORS			{canceled |
					missingParameter |
					parameterOutOfRange |
					systemFailure |
					taskRefused |
					unexpectedComponentSequence |
					unexpectedDataValue |
					unexpectedParameter |
					unavailableResource |
					unknownLegId}
	LINKED			{specializedResourceReport}
	CODE			opcode-playAnnouncement
	}
-- Direction: SCF --> SRF, Timer: Tpa
-- This operation is to be used after Establish Temporary Connection (assist procedure with a second
-- SSP) or a Connect to Resource (no assist) operation. It may be used for inband interaction with
-- an analog user, or for interaction with an ISDN user. In the former case, the SRF is usually
-- collocated with the SSF for standard tones (congestion tone...) or standard announcements. In the
-- latter case, the SRF is always collocated with the SSF in the switch. Any error is returned to
-- the SCF. The timer associated with thisoperation must be of a sufficient duration to allow its 
-- linked operation to be correctly correlated.

PlayAnnouncementArg {PARAMETERS-BOUND : bound}::= SEQUENCE {
	informationToSend			[0] InformationToSend {bound},
	disconnectFromIPForbidden	[1] BOOLEAN	DEFAULT TRUE,
	requestAnnouncementComplete	[2] BOOLEAN	DEFAULT TRUE,
	extensions					[3] SEQUENCE SIZE(1..bound.&numOfExtensions)	OF
																ExtensionField {bound}	OPTIONAL,
																connectedParty	CHOICE {
						legID	[4] LegID,
				callSegmentID	[5] CallSegmentID {bound}
				} 	OPTIONAL,
	...
	}

promptAndCollectUserInformation {PARAMETERS-BOUND : bound} OPERATION :: = {
	ARGUMENT	PromptAndCollectUserInformationArg {bound}
	RESULT		ReceivedInformationArg {bound}
	ERRORS		{canceled |
				improperCallerResponse |
				missingParameter |
				parameterOutOfRange |
				systemFailure |
				taskRefused |
				unexpectedComponentSequence |
				unavailableResource |
				unexpectedDataValue |
				unexpectedParameter
				}
	CODE		opcode-promptAndCollectUserInformation 
	}
-- Direction: SCF --> SRF, Timer: Tpc 
-- This operation is used to interact with a user to collect information.

PromptAndCollectUserInformationArg {PARAMETERS-BOUND : bound}::= SEQUENCE {
	collectedInfo				[0] CollectedInfo,
	disconnectFromIPForbidden	[1] BOOLEAN	DEFAULT TRUE,
	informationToSend 			[2] InformationToSend {bound}	OPTIONAL,
	extensions					[3] SEQUENCE SIZE(1..bound.&numOfExtensions) OF
																ExtensionField {bound}	OPTIONAL,
	callSegmentID				[4] CallSegmentID {bound}								OPTIONAL,
	...
	}

ReceivedInformationArg {PARAMETERS-BOUND : bound}::= CHOICE {
	digitsResponse				[0] Digits {bound},
	iA5Response					[1] IA5String
	}

promptAndReceiveMessage {PARAMETERS-BOUND : bound} OPERATION :: = {
	ARGUMENT	PromptAndReceiveMessageArg {bound}
	RESULT		MessageReceivedArg {bound}
	ERRORS		{canceled |
				improperCallerResponse |
				missingParameter |
				parameterOutOfRange |
				taskRefused |
				systemFailure |
				unavailableResource |
				unexpectedComponentSequence |
				unexpectedDataValue |
				unexpectedParameter |
				unknownSubscriber 
			}
	CODE	opcode-promptAndReceiveMessage
	}
--  Direction: SCF -->SRF, Timer: Tprm
--  Used to prompt a user to store a message

PromptAndReceiveMessageArg {PARAMETERS-BOUND : bound}::= SEQUENCE {
	disconnectFromIPForbidden	[0] BOOLEAN	DEFAULT TRUE,
	informationToSend			[1] InformationToSend {bound}	OPTIONAL,
	extensions					[3] SEQUENCE SIZE(0..bound.&numOfExtensions)	OF
									ExtensionField {bound}	OPTIONAL,
	subscriberID	[4] GenericNumber {bound}	OPTIONAL,
	mailBoxID	[5] MailBoxID {bound}	OPTIONAL,
	informationToRecord	[6] InformationToRecord {bound},
	media	[7] Media 	DEFAULT voiceMail,
	callSegmentID	[8] CallSegmentID {bound}	OPTIONAL,
	...
	}

MessageReceivedArg {PARAMETERS-BOUND : bound}	::= SEQUENCE {
	receivedStatus			[0] ReceivedStatus,
	recordedMessageID		[1] RecordedMessageID	OPTIONAL,
	recordedMessageUnits	[2] INTEGER(1..bound.&maxRecordedMessageUnits)	OPTIONAL,
	extensions				[3] SEQUENCE SIZE(1..bound.&numOfExtensions)	OF
			 													ExtensionField {bound}	OPTIONAL,
	...
	}

scriptClose {PARAMETERS-BOUND : bound} OPERATION :: = {
	ARGUMENT		ScriptCloseArg {bound}
	RETURN RESULT	FALSE
	ERRORS			{
					systemFailure |
					missingParameter |
					taskRefused |
					unavailableResource |
					unexpectedComponentSequence |
					unexpectedDataValue |
					unexpectedParameter 
					}
	CODE			opcode-scriptClose
	}
-- Direction: SCF--> SRF. Timer: TCl
-- This operation is issued by the SCF to deallocate the resources used to perform the
-- instance of the "User Interaction" script: the context is released.

ScriptCloseArg {PARAMETERS-BOUND : bound}::= SEQUENCE {
	uIScriptId	UISCRIPT.&id({SupportedUIScripts {bound}}),
	uIScriptSpecificInfo	[0] UISCRIPT.&SpecificInfo({SupportedUIScripts {bound}}{@uIScriptId})
																						OPTIONAL,
	extensions				[1] SEQUENCE SIZE (1..bound.&numOfExtensions) OF ExtensionField {bound}
																						OPTIONAL,
	callSegmentID		[2] CallSegmentID {bound}										OPTIONAL,
	...
	}

scriptEvent {PARAMETERS-BOUND : bound} OPERATION :: = {
	ARGUMENT		ScriptEventArg {bound}
	RETURN RESULT	FALSE
	ALWAYS RESPONDS	FALSE
	CODE			opcode-scriptEvent
	}
-- Direction: SRF--> SCF. Timer: TRe
-- This operation is issued by the SRF to return information to the SCF on the results of the
-- execution of the instance of User Interaction script.

ScriptEventArg {PARAMETERS-BOUND : bound}::= SEQUENCE {
	uIScriptId		UISCRIPT.&id({SupportedUIScripts {bound}}),
	uIScriptResult	[0] UISCRIPT.&Result({SupportedUIScripts {bound}}{@uIScriptId}) 	OPTIONAL,
	extensions		[1] SEQUENCE SIZE (1..bound.&numOfExtensions) OF ExtensionField {bound}
																						OPTIONAL,
	callSegmentID	[2] CallSegmentID {bound}											OPTIONAL,
	lastEventIndicator
					[3] BOOLEAN 	DEFAULT FALSE,
	...
	}

scriptInformation {PARAMETERS-BOUND : bound} OPERATION :: ={
	ARGUMENT		ScriptInformationArg {bound}
	RETURN RESULT	FALSE
	ERRORS			{systemFailure |
					missingParameter |
					taskRefused |
					unavailableResource |
					unexpectedComponentSequence |
					unexpectedDataValue |
					unexpectedParameter}
	CODE			opcode-scriptInformation
	}
-- Direction: SCF--> SRF. Timer: Tinf

ScriptInformationArg {PARAMETERS-BOUND : bound}::= SEQUENCE {
	uIScriptId			UISCRIPT.&id({SupportedUIScripts {bound}}),
	uIScriptSpecificInfo	[0] UISCRIPT.&SpecificInfo({SupportedUIScripts {bound}}{@uIScriptId})
																						OPTIONAL,
	extensions				[1] SEQUENCE SIZE(0..bound.&numOfExtensions) OF
																ExtensionField {bound}	OPTIONAL,
	callSegmentID			[2] CallSegmentID {bound}									OPTIONAL,
	...
	}

scriptRun {PARAMETERS-BOUND : bound} OPERATION :: ={
	ARGUMENT		ScriptRunArg {bound}
	RETURN RESULT	FALSE
	ERRORS			{systemFailure |
					missingParameter |
					taskRefused |
					unavailableResource |
					unexpectedComponentSequence |
					unexpectedDataValue |
					unexpectedParameter}
	CODE			opcode-scriptRun
	}
-- Direction: SCF --> SRF. Timer: Tru
-- This operation is issued by the SCF to allocate the necessary resources to perform the
-- instance of the "User Interaction" script and then to activate this "User Interaction" script
-- instance. A context is partially defined for it if necessary.

ScriptRunArg {PARAMETERS-BOUND : bound} ::= SEQUENCE {
	uIScriptId				UISCRIPT.&id({SupportedUIScripts {bound}}),
	uIScriptSpecificInfo	[0] UISCRIPT.&SpecificInfo({SupportedUIScripts {bound}}{@uIScriptId})
																						OPTIONAL,
	extensions				[1] SEQUENCE SIZE (1..bound.&numOfExtensions) OF
																ExtensionField {bound}	OPTIONAL,
	disconnectFromIPForbidden
							[2] BOOLEAN												DEFAULT TRUE,
	callSegmentID			[3] CallSegmentID {bound}									OPTIONAL,
	...
	}

specializedResourceReport OPERATION :: = {
	ARGUMENT		SpecializedResourceReportArg
	RETURN RESULT	FALSE
	ALWAYS RESPONDS	FALSE
	CODE			opcode-specializedResourceReport
	}
-- Direction: SRF --> SCF, Timer: Tsrr
-- This operation is used as  the response to a PlayAnnouncement operation when the announcement
-- completed report indication is set.

SpecializedResourceReportArg ::= NULL

END

IN-CS2-SCF-SRF-pkgs-contracts-acs {ccitt recommendation q 1228 modules(0) 
												in-cs2-scf-srf-pkgs-contracts-acs(8) version1(0)}

DEFINITIONS :: =

BEGIN

-- This module describes the operation-packages, contracts and application-contexts used
-- over the SCF-SRF interface.

IMPORTS

	PARAMETERS-BOUND,
	networkSpecificBoundSet,
	emptyConnectionPackage
FROM IN-CS2-classes classes


	ROS-OBJECT-CLASS, CONTRACT, OPERATION-PACKAGE, OPERATION
FROM Remote-Operations-Information-Objects ros-InformationObjects

	TCMessage {} 
FROM TCAPMessages tc-Messages

	APPLICATION-CONTEXT, dialogue-abstract-syntax
FROM TC-Notation-Extensions tc-NotationExtensions

	playAnnouncement {},
	promptAndReceiveMessage {},
	promptAndCollectUserInformation {},
	scriptClose {},
	scriptEvent {},
	scriptInformation {},
	scriptRun {},
	specializedResourceReport
FROM IN-CS2-SCF-SRF-ops-args scf-srf-Operations

	cancel {},
	assistRequestInstructions {}
FROM IN-CS2-SSF-SCF-ops-args ssf-scf-Operations

	srf-scfActivationOfAssistPackage {}
FROM IN-CS2-SSF-SCF-pkgs-contracts-acs ssf-scf-Protocol

	id-package-specializedResourceControl,
	id-ac-srf-scf,
	id-contract-srf-scf,
	id-package-srf-scfCancel,
	id-package-scriptControl,
	id-package-messageControl,
	id-as-basic-srf-scf,
	classes, ros-InformationObjects, tc-Messages, tc-NotationExtensions,
	scf-srf-Operations, ssf-scf-Operations, ssf-scf-Protocol
FROM IN-CS2-object-identifiers {ccitt recommendation q 1228 modules(0) 
														in-cs2-object-identifiers (17) version1(0)}
;

-- Application Contexts 

srf-scf-ac APPLICATION-CONTEXT :: = {
	CONTRACT					srf-scf-contract
	DIALOGUE MODE				structured
	TERMINATION					basic
	ABSTRACT SYNTAXES			{dialogue-abstract-syntax | 
								srf-scf-abstract-syntax}
	APPLICATION CONTEXT NAME	id-ac-srf-scf}

-- Contracts 

srf-scf-contract CONTRACT :: = {
	CONNECTION					emptyConnectionPackage
	INITIATOR CONSUMER OF		{srf-scfActivationOfAssistPackage {networkSpecificBoundSet} }
	RESPONDER CONSUMER OF		{specializedResourceControlPackage {networkSpecificBoundSet}|
								srf-scfCancelPackage {networkSpecificBoundSet}|
								scriptControlPackage {networkSpecificBoundSet}|
								messageControlPackage {networkSpecificBoundSet}}
	ID							id-contract-srf-scf}

-- specializedResourceControl package

specializedResourceControlPackage {PARAMETERS-BOUND : bound} OPERATION-PACKAGE :: = {
	CONSUMER INVOKES	{playAnnouncement {bound} |
						promptAndCollectUserInformation {bound}
	}
	SUPPLIER INVOKES	{specializedResourceReport}
	ID					id-package-specializedResourceControl}

-- srf-scfCancel package

srf-scfCancelPackage {PARAMETERS-BOUND : bound} OPERATION-PACKAGE :: = {
	CONSUMER INVOKES	{cancel {bound}}
	ID					id-package-srf-scfCancel}

-- scriptControl package

scriptControlPackage {PARAMETERS-BOUND : bound} OPERATION-PACKAGE :: = {
	CONSUMER INVOKES	{scriptClose {bound}| scriptRun {bound} | 
						scriptInformation {bound}}
	SUPPLIER INVOKES	{scriptEvent {bound}}
	ID					id-package-scriptControl}

-- messageControl package

messageControlPackage {PARAMETERS-BOUND : bound} OPERATION-PACKAGE :: = {
	CONSUMER INVOKES	{promptAndReceiveMessage {bound}}
	ID					id-package-messageControl}

-- Abstract Syntaxes 

srf-scf-abstract-syntax ABSTRACT-SYNTAX :: = {
	BASIC-SRF-SCF-PDUs
	IDENTIFIED BY	id-as-basic-srf-scf}

BASIC-SRF-SCF-PDUs ::= TCMessage {{SRF-SCF-Invokable},{SRF-SCF-Returnable}}

SRF-SCF-Invokable OPERATION :: = {
		assistRequestInstructions {networkSpecificBoundSet}|
		cancel {networkSpecificBoundSet}|
		playAnnouncement {networkSpecificBoundSet}|
		promptAndCollectUserInformation {networkSpecificBoundSet}|
		scriptClose {networkSpecificBoundSet}|
		scriptEvent {networkSpecificBoundSet}|
		scriptInformation {networkSpecificBoundSet}|
		scriptRun {networkSpecificBoundSet}|
		specializedResourceReport |
		promptAndReceiveMessage {networkSpecificBoundSet}
		}

SRF-SCF-Returnable OPERATION :: = {
		assistRequestInstructions {networkSpecificBoundSet}|
		cancel {networkSpecificBoundSet}|
		playAnnouncement {networkSpecificBoundSet}|
		promptAndCollectUserInformation {networkSpecificBoundSet}|
		scriptClose {networkSpecificBoundSet}|
		scriptInformation {networkSpecificBoundSet}|
		scriptRun {networkSpecificBoundSet}|
		promptAndReceiveMessage {networkSpecificBoundSet}
		}

END

METHOD::= CLASS {
	&InputAttributes 		ATTRIBUTE OPTIONAL,
	&SpecificInput	 		OPTIONAL, 
	&OutputAttributes 		ATTRIBUTE OPTIONAL,
	&SpecificOutput			OPTIONAL, 
	&description			PrintableString OPTIONAL,
	&id 					OBJECT IDENTIFIER UNIQUE}
WITH SYNTAX {
	[INPUT ATTRIBUTES		&InputAttributes]
	[SPECIFIC-INPUT 		&SpecificInput] 
	[OUTPUT ATTRIBUTES		&OutputAttributes]
	[SPECIFIC-OUTPUT		&SpecificOutput] 
	[BEHAVIOUR				&description] 
	ID 						&id}

DITMethodUse ::=	SEQUENCE {
	objectClass		OBJECT-CLASS.&id,
	methods		[1]	SET OF METHOD.&id}

METHOD-USE-RULE ::= CLASS {
	&objectClassType		OBJECT-CLASS.&id	UNIQUE,
	&Mandatory				METHOD}
WITH SYNTAX {
	OBJECT-CLASS TYPE		&objectClassType
	METHODS					&Mandatory}

ProtectedItems	::=	SEQUENCE {
	entry							[0]	NULL OPTIONAL,
	allUserAttributeTypes			[1]	NULL OPTIONAL,
	attributeType					[2]	SET OF AttributeType OPTIONAL,
	allAttributeValues				[3]	SET OF AttributeType OPTIONAL,	
	allUserAttributeTypesAndValues	[4]	NULL OPTIONAL,
	attributeValue					[5]	SET OF AttributeTypeAndValue OPTIONAL,
	selfValue						[6]	SET OF AttributeType OPTIONAL,
	rangeOfValues					[7]	Filter OPTIONAL,
	maxValueCount					[8]	SET OF MaxValueCount OPTIONAL,
	maxImmSub						[9]	INTEGER OPTIONAL,
	restrictedBy					[10] SET OF RestrictedValue OPTIONAL,
	contexts						[11] SET OF ContextAssertion OPTIONAL,
	entryMethods					[30] SET OF MethodIDs OPTIONAL,
...}

MethodIDs ::=	METHOD.&id

GrantsAndDenials			::=	BIT STRING {
	-- permissions that may be used in conjunction with 
	-- with any component of ProtectedItems 
	grantAdd				(0),
	denyAdd					(1),
	grantDiscloseOnError	(2),
	denyDiscloseOnError		(3),
	grantRead				(4),
	denyRead				(5),
	grantRemove				(6),
	denyRemove				(7),
	-- permissions that may be used only in conjunction
	-- with the entry component
	grantBrowse				(8),
	denyBrowse				(9),
	grantExport				(10),
	denyExport				(11),
	grantImport				(12),
	denyImport				(13),
	grantModify				(14),
	denyModify 				(15),
	grantRename				(16),
	denyRename				(17),
	grantReturnDN			(18),
	denyReturnDN			(19),
	-- permissions that may be used in conjunction
	-- with any component, except entry, of ProtectedItems 
	grantCompare			(20),
	denyCompare				(21),
	grantFilterMatch		(22),
	denyFilterMatch			(23),
	-- permissions that may be used in conjunction
	-- with entryMethod component of ProtectedItems 
	grantExecuteMethod		(30),
	denyExecuteMethod		(31)}

basicServiceContext	CONTEXT :: = {
	WITH SYNTAX	BasicService
	ID			id-avc-basicService}

BasicService ::= INTEGER {
	telephony 					(1), 
	faxGroup2-3					(2), 
	faxGroup4 					(3), 
	teletexBasicAndMixed 		(4), 
	teletexBazicAndProcessable	(5), 
	teletexBasic 				(6), 
	syntaxBasedVideotex 		(7), 
	internationalVideotex 		(8), 
	telex 						(9), 
	messageHandlingSystems		(10), 
	osiApplication 				(11), 
	audioVisual 				(12)}

lineIdentityContext	CONTEXT :: = {
	WITH SYNTAX	IsdnAddress
	ID			id-avc-lineIdentity}
IsdnAddress ::= AddressString {ub-international-isdn-number}

assignmentContext	CONTEXT :: = {
	WITH SYNTAX	DistinguishedName
	ID			id-avc-assignment}

methodUse ATTRIBUTE ::= {
	WITH SYNTAX				MethodUseDescription
	EQUALITY MATCHING RULE	objectIdentifierFirstComponentMatch
	USAGE					directoryOperation
	ID						id-soa-methodRuleUse}

MethodUseDescription ::=	SEQUENCE {
	identifier			OBJECT-CLASS.&id,
	name				SET OF DirectoryString {ub-schema} OPTIONAL,
	description			DirectoryString {ub-schema} OPTIONAL,
	obsolete			BOOLEAN DEFAULT FALSE,
	information		[0]	SET OF METHOD.&id
...}

IN-CommonArguments::= CommonArguments (
	WITH COMPONENTS {
		..., 
		serviceControls		(IN-ServiceControls),
		aliasedRDNs			ABSENT})

IN-ServiceControls::= ServiceControls
	(WITH COMPONENTS {
		..., 
		timeLimit			ABSENT,
		sizeLimit			ABSENT,
		scopeOfReferral		ABSENT,
		attributeSizeLimit	ABSENT})

IN-EntryInformationSelection::= EntryInformationSelection
	(WITH COMPONENTS {
		...,
		infoTypes		(attributeTypesAndValues)})

IN-EntryInformation ::= EntryInformation
	(WITH COMPONENTS {
		...,
		fromEntry		(TRUE),
		information		(WITH COMPONENTS {
				...,
				attributeType		ABSENT}) OPTIONAL})

IN-Context-Data::= Context-Data
	(WITH COMPONENTS {
		..., 
		channelId		ABSENT,
		seq-number		ABSENT})

IN-Mic-Header::= Mic-Header
	(WITH COMPONENTS {
		..., 
		snd-seq	ABSENT})

IN-Wrap-Header::= Wrap-Header
	(WITH COMPONENTS {
		..., 
		snd-seq	ABSENT})

IN-Del-Header::= Del-Header
	(WITH COMPONENTS {
		..., 
		snd-seq	ABSENT})

in-DirectoryBind OPERATION :: = {
	ARGUMENT	DirectoryBindArgument
	RESULT		DirectoryBindResult
	ERRORS		{in-DirectoryBindError}
	CODE		in-opcode-in-bind}

in-Search  OPERATION :: = {
	ARGUMENT	IN-SearchArgument
	RESULT		IN-SearchResult
	ERRORS		{nameError | in-ServiceError | securityError | attributeError | referral}
	CODE		id-opcode-in-search}

IN-SearchArgument::= SearchArgument(
	WITH COMPONENTS {
		..., 
		searchAliases		(TRUE),
		selection			(IN-EntryInformationSelection),
		pagedResults		ABSENT,
		extendedFilter		ABSENT,
		COMPONENTS OF 	IN-CommonArguments})})

IN-SearchResult::= SearchResult
	(WITH COMPONENTS {
		...,
		searchInfo		(WITH COMPONENTS {
			...,
			entries	(WITH COMPONENT (IN-EntryInformation)),
			partialOutcomeQualifier	(PartialOutcomeQualifier
					(WITH COMPONENTS {
					...,
					queryReference		ABSENT}))OPTIONAL})})

in-AddEntry  OPERATION :: = {
	ARGUMENT	AddEntryArgument 
	RESULT		AddEntryResult
	ERRORS		{nameError | in-ServiceError | securityError | attributeError | updateError | 
				 referral}
	CODE		id-opcode-in-addEntry}

in-RemoveEntry  OPERATION :: = {
	ARGUMENT	RemoveEntryArgument 
	RESULT		RemoveEntryResult
	ERRORS		{nameError | in-ServiceError | securityError | updateError | referral}
	CODE		id-opcode-in-removeEntry}

in-ModifyEntry  OPERATION :: = {
	ARGUMENT	IN-ModifyEntryArgument 
	RESULT		IN-ModifyEntryResult
	ERRORS		{nameError | in-ServiceError | securityError | attributeError | updateError | 
				referral}
	CODE		id-opcode-in-modifyEntry}
IN-ModifyEntryArgument::= ModifyEntryArgument
	(WITH COMPONENTS {
		..., 
		selection	(IN-EntryInformationSelection)})

The selection parameter specifies some attributes and values to be returned (see subclause 7.3.1.3).
IN-ModifyEntryResult::= ModifyEntryResult
	(WITH COMPONENTS {
		..., 
		null		,
		information	Information
			(WITH COMPONENTS {
				..., 
				entry	(IN-EntryInformation)})}

execute OPERATION :: = {
	ARGUMENT	ExecuteArgument
	RESULT		ExecuteResult
	ERRORS 		{attributeError | nameError | 
				 serviceError | referral | 
				 securityError | 
				 updateError | executionError} 
	CODE		id-opcode-execute}
ExecuteArgument::=  OPTIONALLY-PROTECTED {
	SET {
		object				[0] Name,
		method-id			[1] METHOD.&id({SupportedMethods}),
		input-assertions	[2] SEQUENCE OF SEQUENCE {
					type METHOD.&InputAttributes.&id({SupportedMethods}{@method-id}),
					values SET OF METHOD.&InputAttributes.&id({SupportedMethods}{@method-id}) 																									OPTIONAL, 
					valuesWithContext [0] SET OF SEQUENCE {
							value	[0] METHOD.&InputAttributes.&id({SupportedMethods}{@method-id})
																						OPTIONAL, 
							contextList	[1] SET OF Context 
							} OPTIONAL,
							...
					} OPTIONAL, 
		specific-input	 	[3] METHOD.&SpecificInput({SupportedMethods}{@method-id}) OPTIONAL,
		COMPONENTS OF 	CommonArguments,
		...},
	DIRQOP.&dapModifyEntryArg-QOP{@qop}}

ExecuteResult::= OPTIONALLY-PROTECTED {
	SET {
		method-id		[1] METHOD.&id({SupportedMethods}),
		output-assertions	[2] SEQUENCE OF SEQUENCE {
					type METHOD.&OutputAttributes.&id({SupportedMethods}{@method-id}),
					values	SET OF METHOD.&OutputAttributes.&Type({SupportedMethods}
																{@method-id,@.type})	OPTIONAL, 
					valuesWithContext [0] SET OF SEQUENCE {
						value	[0] 	METHOD.&OutputAttributes.&Type({SupportedMethods}
																{@method-id,@.type})	OPTIONAL, 
						contextList	[1] SET OF Context 
						} OPTIONAL,
						...
					} OPTIONAL, 
		specific-output	[3] METHOD.&SpecificOutput({SupportedMethods}{@method-id}) 		OPTIONAL,
		COMPONENTS OF CommonResults,
		...},
	DIRQOP.&dapModifyEntryRes-QOP{@qop}}

SupportedMethods METHOD ::= { ...}

in-directoryUnbind  OPERATION :: = inEmptyUnbind

IN-DirectoryBindError::= DirectoryBindError
	(WITH COMPONENTS {
		...,
		error	(WITH COMPONENTS {
						securityError (SecurityProblem (1|2|7|10)),
						serviceError (ServiceProblem (2))})})

in-ServiceError ERROR::= {
	PARAMETER	IN-ServiceErrorParameter
	CODE		id-errcode-in-serviceError}

IN-ServiceErrorParameter::=ServiceErrorParameter
	(WITH COMPONENTS {
		problem	(ServiceProblem (1 | 2 | 3 | 4 |5 | 6 | 8 | 9 | 10 | 11 | 12))})

executionError ERROR::= {
	PARAMETER	OPTIONALLY-PROTECTED {
				SET {
					problem 	[0] 	ExecutionProblem,
					COMPONENTS OF CommonResults},
				DIRQOP.&dirErrors-QOP{@dirqop}}
	CODE 			id-errcode-executionError} 
ExecutionProblem ::=  INTEGER {
	missingInputValues (1),
	executionFailure (2)} 

dua ROS-OBJECT-CLASS::= {
	INITIATES 	{dapContract| dapExecuteContract}
	ID	 		id-rosObject-dua}

directory ROS-OBJECT-CLASS::= {
	RESPONDS	{dapContract| dapExecuteContract}
	ID			id-rosObject-directory}

dap-dsa ROS-OBJECT-CLASS::= {
	RESPONDS	{dapContract| dapExecuteContract}
	ID			id-rosObject-dapDSA}

dapContract CONTRACT :: = {
	CONNECTION 			dapConnectionPackage
	INITIATOR CONSUMER OF	{searchPackage | modifyPackage}
	ID 					id-contract-dap}

dapExecuteContract CONTRACT :: = {
	CONNECTION			dapConnectionPackage
	INITIATOR CONSUMER OF	{searchPackage | modifyPackage | executePackage}
	ID					id-contract-dapExecute}

dapConnectionPackage CONNECTION-PACKAGE::= {
	BIND			in-DirectoryBind 
	UNBIND		in-directoryUnbind
	ID			id-package-dapConnection}

searchPackage OPERATION-PACKAGE :: = {
	CONSUMER INVOKES	{search}
	ID					id-package-search}
modifyPackage OPERATION-PACKAGE :: = {
	CONSUMER INVOKES	{addEntry | removeEntry | modifyEntry}
	ID 					id-package-modify}

executePackage OPERATION-PACKAGE :: = {
	CONSUMER INVOKES	{execute}
	ID					id-package-execute}

inDirectoryOperationsAbstractSyntax ABSTRACT-SYNTAX :: = {
	BasicDAP-PDUs
	IDENTIFIED BY	id-as-indirectoryOperationsAS}
BasicDAP-PDUs :: = TCMessage {{DAP-Invokable}, {DAP-Returnable}}
DAP-Invokable  OPERATION :: = {search | addEntry | removeEntry | modifyEntry}
DAP-Returnable OPERATION :: = {search | addEntry | removeEntry | modifyEntry} 

inExtendedDirectoryOperationsAbstractSyntax ABSTRACT-SYNTAX :: = {
	Extended-BasicDAP-PDUs
	IDENTIFIED BY	id-as-inExtendedDirectoryOperationsAS}
Extended-BasicDAP-PDUs :: = TCMessage {{Extended-DAP-Invokable},{Extended-DAP-Returnable}}
Extended-DAP-Invokable  OPERATION :: = {search | addEntry | removeEntry | modifyEntry | execute}
Extended-DAP-Returnable OPERATION :: = {search | addEntry | removeEntry | modifyEntry | execute} 

inDirectoryBindingAbstractSyntax	ABSTRACT-SYNTAX :: = {
	DAPBinding-PDUs
	IDENTIFIED BY	id-as-indirectoryBindingAS}
DAPBinding-PDUs :: = CHOICE {
	bind	Bind {directoryBind},
	unbind	Unbind {in-directoryUnbind}}

inSESEAbstractSyntax 	ABSTRACT-SYNTAX :: = {
	SESEapdus {{spkmThreeWay},NoInvocationId}
	IDENTIFIED BY	{id-as-inSESEAS}}

iNdirectoryAccessAC APPLICATION-CONTEXT :: =  {
	CONTRACT					dapContract 
	DIALOGUE MODE				structured
	TERMINATION					basic
	ABSTRACT SYNTAXES			{dialogue-abstract-syntax |
								inDirectoryOperationsAbstractSyntax |
								inDirectoryBindingAbstractSyntax}
	APPLICATION CONTEXT NAME	id-ac-indirectoryAccessAC}

iNdirectoryAccessWith3seAC APPLICATION-CONTEXT :: =  {
	CONTRACT					dapContract 
	DIALOGUE MODE				structured
	TERMINATION					basic
	ADDITIONAL ASE				{id-se-threewayse}
	ABSTRACT SYNTAXES			{dialogue-abstract-syntax |
								inDirectoryOperationsAbstractSyntax |
								inDirectoryBindingAbstractSyntax |
								inSESEAbstractSyntax}
	APPLICATION CONTEXT NAME	id-ac-indirectoryAccessWith3seAC}

inExtendedDirectoryAccessAC APPLICATION-CONTEXT :: =  {
	CONTRACT					dapExecuteContract 
	DIALOGUE MODE				structured
	TERMINATION					basic
	ABSTRACT SYNTAXES			{dialogue-abstract-syntax |
								inExtendedDirectoryOperationsAbstractSyntax |
								inDirectoryBindingAbstractSyntax}
	APPLICATION CONTEXT NAME	id-ac-inExtendedDirectoryAccessAC}

inExtendedDirectoryAccessWith3seAC APPLICATION-CONTEXT :: =  {
	CONTRACT					dapExecuteContract 
	DIALOGUE MODE				structured
	TERMINATION					basic
	ADDITIONAL ASE				{id-se-threewayse} 
	ABSTRACT SYNTAXES			{dialogue-abstract-syntax |
								inExtendedDirectoryOperationsAbstractSyntax |
								inExtendedDirectoryBindingAbstractSyntax |
								inSESEAbstractSyntax}
	APPLICATION CONTEXT NAME	id-ac-inExtendedDirectoryAccessWith3seAC}

IN-CS2-SDF-InformationFramework {ccitt r q 1228 module(0) sdfInformationFramework(9) version1(0)}
DEFINITIONS :: =
BEGIN
-- EXPORTS ALL --
-- types and values are exported for use in the ASN.1 modules which define the IN profile of the
-- Directory
-- Abstract Service, the Directory Access Protocol and the Directory Information Shadowing 
-- Protocol.
-- The types and values defined in this module are exported for use in the other ASN.1 modules
-- contained within the Directory Specifications, and for the use of other applications which will
-- use them to access Directory services. Other applications may use them for their own purposes,
-- but this will not constrainextensions and modifications needed to maintain or improve the
-- Directory service.

IMPORTS 
informationFramework, upperBounds, selectedAttributeTypes 
	FROM UsefulDefinitions {joint-iso-ccitt ds(5) module(1) usefulDefinitions(0) 3}

ATTRIBUTE, OBJECT-CLASS, objectClass, aliasedEntryName
	FROM InformationFramework	informationFramework

DirectoryString{}, objectIdentifierFirstComponentMatch 
	FROM SelectedAttributeTypes	selectedAttributeTypes

ub-schema 
	FROM UpperBounds			upperBounds

id-soa-methodRuleUse
	FROM IN-CS2-object-identifiers
		{ccitt recommendation q 1228 modules(0) in-cs2-object-identifiers(17) version1(0)}
; 

-- attribute data types --
--	Definition of the following information object set is deferred, perhaps to standardized
--	profiles or to protocol implementation conformance statements. The set is required to
--	specify a table constraint on the values component of Attribute, the value component 
--	of AttributeTypeAndValue, and the assertion component of AttributeValueAssertion.

SupportedAttributes ATTRIBUTE::= {objectClass | aliasedEntryName, ...}

-- METHOD information object class specification --
METHOD::= CLASS {
	&InputAttributes 		ATTRIBUTE OPTIONAL,
	&SpecificInput	 		OPTIONAL, 
	&OutputAttributes 		ATTRIBUTE OPTIONAL,
	&SpecificOutput			OPTIONAL, 
	&description			PrintableString OPTIONAL,
	&id 					OBJECT IDENTIFIER UNIQUE}
WITH SYNTAX {
	[INPUT ATTRIBUTES		&InputAttributes]
	[SPECIFIC-INPUT 		&SpecificInput] 
	[OUTPUT ATTRIBUTES		&OutputAttributes]
	[SPECIFIC-OUTPUT		&SpecificOutput] 
	[BEHAVIOUR				&description] 
	ID 						&id}

DITMethodUse	::=	SEQUENCE {
	objectClass		OBJECT-CLASS.&id,
	methods		[1]	SET OF METHOD.&id,
	...}
METHOD-USE-RULE::= CLASS {
	&objectClassType	OBJECT-CLASS.&id	UNIQUE,
	&Mandatory			METHOD}
WITH SYNTAX {
	OBJECT-CLASS TYPE		&objectClassType
	METHODS					&Mandatory}
-- attributes --
methodUse ATTRIBUTE::= {
	WITH SYNTAX				MethodUseDescription
	EQUALITY MATCHING RULE	objectIdentifierFirstComponentMatch
	USAGE					directoryOperation
	ID						id-soa-methodRuleUse}
MethodUseDescription	::=	SEQUENCE {
	identifier			OBJECT-CLASS.&id,
	name				SET OF DirectoryString {ub-schema} OPTIONAL,
	description			DirectoryString {ub-schema} OPTIONAL,
	obsolete			BOOLEAN DEFAULT FALSE,
	information		[0]	SET OF METHOD.&id,
	...}
END

IN-CS2-SDF-BasicAccessControl
		{ccitt recommendation q 1228 module(0) sdfBasicAccessControl(10) version1(0)}
DEFINITIONS :: =
BEGIN
-- EXPORTS All --
-- The types and values defined in this module are exported for use in the other ASN.1 modules 
-- contained within the Directory Specifications, and for the use of other applications which will
-- use them to access Directory services. Other applications may use them for their own purposes,
-- but this will not constrainextensions and modifications needed to maintain or improve the
-- Directory service.

IMPORTS

informationFramework, upperBounds, selectedAttributeTypes, basicAccessControl, directoryAbstractService 
	FROM UsefulDefinitions {joint-iso-ccitt ds(5) module(1) usefulDefinitions(0) 3}

ATTRIBUTE, AttributeType, AttributeTypeAndValue, SubtreeSpecification, ContextAssertion
	FROM InformationFramework informationFramework
id-aca-prescriptiveACI, id-aca-entryACI, id-aca-subentryACI,
sdf-InformationFramework
	FROM IN-CS2-object-identifiers
		{ccitt recommendation q 1228 modules(0) in-cs2-object-identifiers(17) version1(0)}

ub-tag
	FROM UpperBounds upperBounds
METHOD
	FROM IN-CS2-SDF-InformationFramework 

sdf-InformationFramework
Filter
	FROM DirectoryAbstractService directoryAbstractService

NameAndOptionalUID, directoryStringFirstComponentMatch, DirectoryString{}
	FROM SelectedAttributeTypes selectedAttributeTypes 

MaxValueCount, RestrictedValue, AuthenticationLevel, Precedence
	FROM BasicAccessControl basicAccessControl
;

-- types --
ACIItem		::=		SEQUENCE {
	identificationTag		DirectoryString {ub-tag},
	precedence				Precedence,
	authenticationLevel		AuthenticationLevel,
	itemOrUserFirst			CHOICE {
		itemFirst				[0]	SEQUENCE {
			protectedItems			ProtectedItems,
			itemPermissions			SET OF ItemPermission,
			...},
		userFirst				[1]	SEQUENCE {
			userClasses				UserClasses,
			userPermissions			SET OF UserPermission,
			...},
		},
	...}
ProtectedItems	::=	SEQUENCE {
	entry							[0]	NULL OPTIONAL,
	allUserAttributeTypes			[1]	NULL OPTIONAL,
	attributeType					[2]	SET OF AttributeType OPTIONAL,
	allAttributeValues				[3]	SET OF AttributeType OPTIONAL,	allUserAttributeTypesAndValues	[4]	NULL OPTIONAL,
	attributeValue					[5]	SET OF AttributeTypeAndValue OPTIONAL,
	selfValue						[6]	SET OF AttributeType OPTIONAL,
	rangeOfValues					[7]	Filter OPTIONAL,
	maxValueCount					[8]	SET OF MaxValueCount OPTIONAL,
	maxImmSub						[9]	INTEGER OPTIONAL,
	restrictedBy					[10] SET OF RestrictedValue OPTIONAL,
	contexts						[11] SET OF ContextAssertion OPTIONAL,
	entryMethods					[30] SET OF MethodIDs OPTIONAL,
	...}
MethodIDs::=	METHOD.&id
UserClasses	::=	SEQUENCE {
	allUsers	[0]	NULL OPTIONAL,
	thisEntry	[1]	NULL OPTIONAL,
	name		[2]	SET OF NameAndOptionalUID OPTIONAL,
	userGroup	[3]	SET OF NameAndOptionalUID OPTIONAL,
					-- dn component must be the name of an
					-- entry of GroupOfUniqueNames 
	subtree	[4]	SET OF SubtreeSpecification OPTIONAL,
	...}
ItemPermission			::=	SEQUENCE {
	precedence			Precedence OPTIONAL, 
						-- defaults to precedence in ACIItem --
	userClasses			UserClasses,
	grantsAndDenials	GrantsAndDenials,
	...}
UserPermission			::=	SEQUENCE {
	precedence			Precedence OPTIONAL, 
						-- defaults to precedence in ACIItem
	protectedItems		ProtectedItems,
	grantsAndDenials	GrantsAndDenials,
	...}
GrantsAndDenials			::=	BIT STRING {
	-- permissions that may be used in conjunction with 
	-- with any component of ProtectedItems 
	grantAdd				(0),
	denyAdd					(1),
	grantDiscloseOnError	(2),
	denyDiscloseOnError		(3),
	grantRead				(4),
	denyRead				(5),
	grantRemove				(6),
	denyRemove				(7),
	-- permissions that may be used only in conjunction
	-- with the entry component
	grantBrowse				(8),
	denyBrowse				(9),
	grantExport				(10),
	denyExport				(11),
	grantImport				(12),
	denyImport				(13),
	grantModify				(14),
	denyModify 				(15),
	grantRename		 		(16),
	denyRename				(17),
	grantReturnDN			(18),
	denyReturnDN			(19),
	-- permissions that may be used in conjunction
	-- with any component, except entry, of ProtectedItems 
	grantCompare			(20),
	denyCompare				(21),
	grantFilterMatch		(22),
	denyFilterMatch			(23),
	-- permissions that may be used in conjunction
	-- with entryMethod component of ProtectedItems 
	grantExecuteMethod		(30),
	denyExecuteMethod		(31)}

-- attributes --
prescriptiveACI		ATTRIBUTE::=	{
	WITH SYNTAX				ACIItem
	EQUALITY MATCHING RULE	directoryStringFirstComponentMatch
	USAGE					directoryOperation
	ID						id-aca-prescriptiveACI}
entryACI			ATTRIBUTE::=	{
	WITH SYNTAX				ACIItem
	EQUALITY MATCHING RULE	directoryStringFirstComponentMatch
	USAGE					directoryOperation
	ID						id-aca-entryACI}
subentryACI 		ATTRIBUTE::=	{
	WITH SYNTAX				ACIItem
	EQUALITY MATCHING RULE	directoryStringFirstComponentMatch
	USAGE					directoryOperation
	ID						id-aca-subentryACI}
END


IN-CS2-SCF-SDF-Operations 
			{ccitt recommendation q 1228 module(0) scf-sdf-operations(11) version1(0)}
DEFINITIONS :: =
BEGIN
-- EXPORTS All --
-- The types and values defined in this module are exported for use in the other ASN.1 modules
-- contained within the IN Directory Specifications, and for the use of other applications which
-- will use them to access IN Directory services. Other applications may use them for their own
-- purposes, but this will not constrain extensions and modifications needed to maintain or improve 
-- the Directory service.

IMPORTS

informationFramework, distributedOperations, authenticationFramework, upperBounds, 
directoryAbstractService, enhancedSecurity 
	FROM UsefulDefinitions {joint-iso-ccitt ds(5) module(1) usefulDefinitions(0) 3} 

CONTEXT, Context, DistinguishedName, Name 
	FROM InformationFramework informationFramework

OperationProgress, ReferenceType, Exclusions, AccessPoint, ContinuationReference 
	FROM DistributedOperations distributedOperations

CertificationPath, SIGNED {}, SIGNATURE {}, AlgorithmIdentifier
	FROM AuthenticationFramework authenticationFramework

id-avc-assignment,
contexts, ros-InformationObjects, sdf-InformationFramework
	FROM IN-CS2-object-identifiers
		{ccitt recommendation q 1228 modules(0) in-cs2-object-identifiers(17) version1(0)}

basicServiceContext, lineIdentityContext
	FROM IN-Contexts    contexts

Code, OPERATION, ERROR
	FROM Remote-Operations-Information-Objects ros-InformationObjects

inEmptyUnbind
	FROM IN-CS2-classes {ccitt recommendation q 1228 modules(0) in-cs2-classes(4) version1(0)}

METHOD 
	FROM IN-CS2-SDF-InformationFramework

sdf-InformationFramework
OPTIONALLY-PROTECTED{}, DIRQOP
	FROM EnhancedSecurity enhancedSecurity

CommonArguments, CommonResults, attributeError, nameError, serviceError, securityError, referral, updateError
	FROM DirectoryAbstractService	 directoryAbstractService
;

execute OPERATION :: = {
	ARGUMENT	ExecuteArgument
	RESULT		ExecuteResult
	ERRORS 		{attributeError | nameError | 
				 serviceError | referral | 
				 securityError | 
				 updateError | executionError} 
	CODE		id-opcode-execute}
ExecuteArgument ::=  OPTIONALLY-PROTECTED {
	SET {
		object 				[0] Name,
		method-id 			[1] METHOD.&id({SupportedMethods}),
		input-assertions	[2] SEQUENCE OF SEQUENCE {
								type 	METHOD.&InputAttributes.&id({SupportedMethods}{@method-id}),
								values	SET OF
					METHOD.&InputAttributes.&Type({SupportedMethods}{@method-id,@.type}) OPTIONAL, 
								valuesWithContext [0] SET OF SEQUENCE {
									value	[0]	
				METHOD.&InputAttributes.&Type({SupportedMethods}{@method-id,@.type})	OPTIONAL, 
								contextList [1] 	SET OF Context 
								} OPTIONAL,
								...
							} OPTIONAL, 
		specific-input		[3] METHOD.&SpecificInput({SupportedMethods}{@method-id}) OPTIONAL,
		COMPONENTS OF CommonArguments,
		...},
	DIRQOP.&dapModifyEntryArg-QOP{@qop}}

ExecuteResult ::= OPTIONALLY-PROTECTED {
	SET {
		method-id			[1] METHOD.&id({SupportedMethods}),
		output-assertions	[2] SEQUENCE OF SEQUENCE {
							type 	METHOD.&OutputAttributes.&id({SupportedMethods}{@method-id}),
							values	SET OF METHOD.&OutputAttributes.&Type({SupportedMethods}{@method-id,@.type})OPTIONAL, 
							valuesWithContext [0] SET OF SEQUENCE {
								value		[0] 	METHOD.&OutputAttributes.&Type({SupportedMethods}{@method-id,@.type})	OPTIONAL, 
								contextList	[1] SET OF Context 
								} OPTIONAL,
								...
							} OPTIONAL, 
		specific-output		[3] METHOD.&SpecificOutput({SupportedMethods}{@method-id}) OPTIONAL, 
		COMPONENTS OF CommonResults,
		...},
	DIRQOP.&dapModifyEntryRes-QOP{@qop}}

SupportedMethods METHOD ::= {...}
in-directoryUnbind  OPERATION :: = inEmptyUnbind
assignmentContext	CONTEXT :: = {
	WITH SYNTAX	DistinguishedName
	ID			id-avc-assignment}

executionError ERROR ::= {
	PARAMETER	OPTIONALLY-PROTECTED {
					SET {
						problem 	[0] 	ExecutionProblem,
						COMPONENTS OF CommonResults},
					DIRQOP.&dirErrors-QOP{@dirqop}}
	CODE 			id-errcode-executionError} 
ExecutionProblem ::=  INTEGER {
	missingInputValues	(1),
	executionFailure	(2)} 
-- object identifier assignment
-- error codes
id-errcode-executionError		Code::= local: 10
-- operation codes
id-opcode-execute				Code::= local: 10

END

IN-CS2-SCF-SDF-Protocol {ccitt ITU-T Recommendation q 1218 modules(0) in-scf-sdf-protocol(12) version1(0)} 
DEFINITIONS :: =
BEGIN 
-- EXPORTS All --
-- The types and values defined in this module are exported for use in the other ASN.1 modules
-- contained within the Directory Specifications, and for the use of other applications which will
-- use them to access Directory services. Other applications may use them for their own purposes,
-- but this will not constrain extensions and modifications needed to maintain or improve the
-- Directory service. 

IMPORTS 

directoryAbstractService, directorySecurityExchanges, protocolObjectIdentifiers
	FROM UsefulDefinitions ds-UsefulDefinitions

ROS-OBJECT-CLASS, CONTRACT, OPERATION-PACKAGE, CONNECTION-PACKAGE, 
OPERATION 
	FROM Remote-Operations-Information-Objects ros-InformationObjects

Bind{}, Unbind{} 
	FROM Remote-Operations-Generic-ROS-PDUs ros-genericPDUs

TCMessage {}
	FROM TCAPMessages tc-Messages

APPLICATION-CONTEXT, dialogue-abstract-syntax
	FROM TC-Notation-Extensions tc-NotationExtensions

id-ac-indirectoryAccessAC, id-ac-inExtendedDirectoryAccessAC, id-rosObject-dua, id-rosObject-directory, 
id-rosObject-dapDSA, 
id-contract-dap, id-contract-dapExecute, id-package-dapConnection, id-package-search, id-package-modify, 
id-package-execute,
id-as-indirectoryOperationsAS, id-as-inExtendedDirectoryOperationsAS, id-as-indirectoryBindingAS, 
id-as-inSESEAS,
id-ac-inExtendedDirectoryAccessWith3seAC, id-ac-indirectoryAccessWith3seAC,
ros-InformationObjects, ros-genericPDUs, tc-Messages, tc-NotationExtensions, sese-APDUs,
ds-UsefulDefinitions, scf-sdf-Operations
	FROM IN-CS2-object-identifiers
		{ccitt recommendation q 1228 modules(0) in-cs2-object-identifiers (17) version1 (0)}

directoryBind, search, addEntry, removeEntry, modifyEntry 
	FROM DirectoryAbstractService directoryAbstractService

SESEapdus{}, NoInvocationId
	FROM SeseAPDUs sese-APDUs

spkmThreeWay
	FROM DirectorySecurityExchanges directorySecurityExchanges

id-se-threewayse 
	FROM ProtocolObjectIdentifiers protocolObjectIdentifiers

execute, in-directoryUnbind
	FROM IN-CS2-SCF-SDF-Operations 

scf-sdf-Operations
; 

-- application contexts -- 

iNdirectoryAccessAC APPLICATION-CONTEXT :: =  {
 	CONTRACT			dapContract 
	DIALOGUE MODE		structured
	TERMINATION				basic
	ABSTRACT SYNTAXES		{dialogue-abstract-syntax |
							inDirectoryOperationsAbstractSyntax |
							inDirectoryBindingAbstractSyntax}
	APPLICATION CONTEXT NAME	id-ac-indirectoryAccessAC}

iNdirectoryAccessWith3seAC APPLICATION-CONTEXT :: =  {
	CONTRACT			dapContract 
	DIALOGUE MODE		structured
	TERMINATION				basic
	ADDITIONAL ASE		{id-se-threewayse}
	ABSTRACT SYNTAXES			{dialogue-abstract-syntax |
						inDirectoryOperationsAbstractSyntax |
						inDirectoryBindingAbstractSyntax |
						inSESEAbstractSyntax}
	APPLICATION CONTEXT NAME	id-ac-indirectoryAccessWith3seAC}

inExtendedDirectoryAccessAC APPLICATION-CONTEXT :: =  {
	CONTRACT			dapExecuteContract 
	DIALOGUE MODE		structured
	TERMINATION				basic
	ABSTRACT SYNTAXES		{dialogue-abstract-syntax |
							inExtendedDirectoryOperationsAbstractSyntax |
							inDirectoryBindingAbstractSyntax}
	APPLICATION CONTEXT NAME	id-ac-inExtendedDirectoryAccessAC}

inExtendedDirectoryAccessWith3seAC APPLICATION-CONTEXT :: =  {
	CONTRACT			dapExecuteContract 
	DIALOGUE MODE		structured
	TERMINATION			basic
	ADDITIONAL ASE		{id-se-threewayse} 
	ABSTRACT SYNTAXES		{dialogue-abstract-syntax |
						inExtendedDirectoryOperationsAbstractSyntax |
						inDirectoryBindingAbstractSyntax |
						inSESEAbstractSyntax}
	APPLICATION CONTEXT NAME	id-ac-inExtendedDirectoryAccessWith3seAC}

-- ROS-objects --

dua ROS-OBJECT-CLASS::= {
	INITIATES 	{dapContract| dapExecuteContract}
	ID	 		id-rosObject-dua}
directory ROS-OBJECT-CLASS::= {
	RESPONDS	{dapContract| dapExecuteContract}
	ID			id-rosObject-directory}
dap-dsa ROS-OBJECT-CLASS::= {
	RESPONDS	{dapContract| dapExecuteContract}
	ID			id-rosObject-dapDSA}

-- contracts --

dapContract CONTRACT :: = {
	CONNECTION 			dapConnectionPackage
	INITIATOR CONSUMER OF	{searchPackage | modifyPackage}
	ID 					id-contract-dap}
dapExecuteContract CONTRACT :: = {
	CONNECTION			dapConnectionPackage
	INITIATOR CONSUMER OF	{searchPackage | modifyPackage | executePackage}
	ID					id-contract-dapExecute}

-- connection package --

dapConnectionPackage CONNECTION-PACKAGE::= {
	BIND		directoryBind 
	UNBIND		in-directoryUnbind
	ID			id-package-dapConnection}

--  search and modify packages

searchPackage OPERATION-PACKAGE :: = {
	CONSUMER INVOKES		{search}
	ID				id-package-search}
modifyPackage OPERATION-PACKAGE :: = {
	CONSUMER INVOKES		{addEntry | removeEntry | modifyEntry}
	ID 				id-package-modify}
executePackage OPERATION-PACKAGE :: = {
	CONSUMER INVOKES	{execute}
	ID				id-package-execute}

-- abstract-syntaxes --

inDirectoryOperationsAbstractSyntax ABSTRACT-SYNTAX :: = {
	BasicDAP-PDUs
	IDENTIFIED BY	id-as-indirectoryOperationsAS}
BasicDAP-PDUs :: = TCMessage {{DAP-Invokable},{DAP-Returnable}}
DAP-Invokable  OPERATION :: = {search | addEntry | removeEntry | modifyEntry}
DAP-Returnable OPERATION :: = {search | addEntry | removeEntry | modifyEntry} 
inExtendedDirectoryOperationsAbstractSyntax ABSTRACT-SYNTAX :: = {
	Extended-BasicDAP-PDUs
	IDENTIFIED BY	id-as-inExtendedDirectoryOperationsAS}
Extended-BasicDAP-PDUs :: = TCMessage {{Extended-DAP-Invokable},{Extended-DAP-Returnable}}
Extended-DAP-Invokable  OPERATION :: = {search | addEntry | removeEntry | modifyEntry | execute}
Extended-DAP-Returnable OPERATION :: = {search | addEntry | removeEntry | modifyEntry | execute} 
inDirectoryBindingAbstractSyntax	ABSTRACT-SYNTAX :: = {
	DAPBinding-PDUs
	IDENTIFIED BY	id-as-indirectoryBindingAS}
DAPBinding-PDUs :: = CHOICE {
	bind	Bind {directoryBind},
	unbind	Unbind {in-directoryUnbind}}
inSESEAbstractSyntax 	ABSTRACT-SYNTAX :: = {
	SESEapdus {{spkmThreeWay},NoInvocationId}
	IDENTIFIED BY	{id-as-inSESEAS}}
END

IN-ShadowingAgreementInfo ::= ShadowingAgreementInfo (
	WITH COMPONENTS {
		...,
		master			ABSENT, 
		secondaryShadows		ABSENT})

in-dSAShadowBind OPERATION :: = in-DirectoryBind

inCoordinateShadowUpdate  OPERATION :: = {
	ARGUMENT	IN-CoordinateShadowUpdateArgument
	RESULT		IN-CoordinateShadowUpdateResult
	ERRORS		{shadowError}
	CODE		id-opcode-coordinateShadowUpdate}
IN-CoordinateShadowUpdateArgument 	::= CoordinateShadowUpdateArgument (
	WITH COMPONENTS {
		..., 
		updateStrategy	(standard: {total | incremental})})
IN-CoordinateShadowUpdateResult 	::=	CoordinateShadowUpdateResult(
	WITH COMPONENTS {
		...,
		null		PRESENT})

inUpdateShadow  OPERATION :: = {
	ARGUMENT	IN-UpdateShadowArgument
	RESULT		IN-UpdateShadowResult
	ERRORS		{shadowError}
	CODE		id-opcode-updateShadow}
IN-UpdateShadowArgument::= UpdateShadowArgument (
	WITH COMPONENTS {
		..., 
		updatedInfo		(IN-RefreshInformation)})
IN-UpdateShadowResult	::=	UpdateShadowUpdateResult(
	WITH COMPONENTS {
		...,
		null		PRESENT})

IN-RefreshInformation::= RefreshInformation (
	WITH COMPONENTS {
		..., 
		otherStrategy		ABSENT})

inRequestShadowUpdate  OPERATION :: = {
	ARGUMENT	IN-RequestShadowUpdateArgument
	RESULT		IN-RequestShadowUpdateResult
	ERRORS		{shadowError}
	CODE		id-opcode-RequestShadowUpdate}
IN-RequestShadowUpdateArgument::= RequestShadowUpdateArgument (
	WITH COMPONENTS {
		..., 
		requestedStrategy 	(standard: {incremental | total})})
IN-RequestShadowUpdateResult::= RequestShadowUpdateResult(
	WITH COMPONENTS {
		...,
		null		PRESENT})

IN-ChainingArguments::= ChainingArguments (
	WITH COMPONENTS {
		..., 
		aliasDereferenced		ABSENT, 
		aliasedRDNs			ABSENT, 
		returnCrossRefs		ABSENT, 
		info				ABSENT, 
		timeLimit			ABSENT, 
		excludeShadows		ABSENT, 
		nameResolveOnMaster	ABSENT})

IN-ChainingResults::= ChainingResults (
	WITH COMPONENTS {
		..., 
		info			ABSENT, 
		crossReferences	ABSENT})

IN-ReferenceType ::= ReferenceType (1|2|4|5|6|7|8)

IN-AccessPoint ::= AccessPoint (
	WITH COMPONENTS {
		.., 
		protocolInformation	ABSENT})

IN-MasterOrShadowAccessPoint ::= MasterOrShadowAccessPoint (
	WITH COMPONENTS {
		...,
		COMPONENTS OF IN-AccessPoint})

IN-MasterAndShadowAccessPoints	::= MasterOrShadowAccessPoint

IN-AccessPointInformation ::= AccessPointInformation (
	WITH COMPONENTS {
		..., 
		COMPONENTS OF IN-MasterOrShadowAccessPoint})

IN-ContinuationReference	::=	ContinuationReference (
	WITH COMPONENTS {
		..., 
		aliasedRDNs			ABSENT, 
		rdnsResolved		ABSENT, 
		referenceType		(IN-ReferenceType), 
		accessPoints 			SET OF (IN-AccessPoint)) 

dSABind OPERATION :: = in-DirectoryBind

in-DSAUnbind  OPERATION :: = inEmptyUnbind

IN-chained {OPERATION: operation} OPERATION 	::= {
	ARGUMENT	OPTIONALLY-PROTECTED {SET {
		chainedArgument		(IN-ChainingArguments), 
		argument 		[0]	operation.&ArgumentType},
		DIRQOP.&dspChainedOp-QOP@dirqop}
	RESULT	OPTIONALLY-PROTECTED {SET {
		IN-chainedResult		ABSENT, 
		result			[0]	operation.&ResultType},
		DIRQOP.&dspChainedOp-QOP@dirqop}
	ERRORS	{operation.&Errors EXCEPT (referral | dsaReferral)}
	CODE	operation.&code}

IN-dsaReferral  ERROR ::= dsaReferral (
	WITH COMPONENTS {
		...,
		reference		(IN-ContinuationReference),
		contextPrefix		ABSENT})

dsp-dsa  ROS-OBJECT-CLASS::= {
	BOTH	{indspContract}
	ID		id-rosObject-dspDSA}

initiating-consumer-dsa  ROS-OBJECT-CLASS::= {
	INITIATES	{shadowConsumerContract}
	ID		id-rosObject-initiatingConsumerDSA}
responding-supplier-dsa  ROS-OBJECT-CLASS::= {
	RESPONDS	{shadowConsumerContract}
	ID		id-rosObject-respondingSupplierDSA}

initiating-supplier-dsa  ROS-OBJECT-CLASS::= {
	INITIATES	{shadowSupplierContract}
	ID		id-rosObject-initiatingSupplierDSA}
responding-consumer-dsa  ROS-OBJECT-CLASS::= {
	RESPONDS	{shadowSupplierContract}
	ID		id-rosObject-respondingConsumerDSA}

indspContract  CONTRACT :: = {
	CONNECTION			dspConnectionPackage
	INITIATOR CONSUMER OF	{inchainedModifyPackage | inchainedSearchPackage | 
							chainedExecutePackage}
	ID					id-contract-indsp}

dspConnectionPackage  CONNECTION-PACKAGE::= {
	BIND		dSABind
	UNBIND		in-DSAUnbind
	ID			id-package-dspConnection}

inchainedModifyPackage  OPERATION-PACKAGE :: = {
	CONSUMER INVOKES	{chainedAddEntry | chainedRemoveEntry | chainedModifyEntry}
	ID			id-package-inchainedModify}
inchainedSearchPackage OPERATION-PACKAGE :: = {
	CONSUMER INVOKES	{chainedSearch}
	ID			id-package-inchainedSearch}

chainedExecutePackage  OPERATION-PACKAGE :: = {
	CONSUMER INVOKES	{chainedExecute}
	ID			id-package-inchainedExecute}

shadowConsumerContract  CONTRACT :: = {
	CONNECTION			dispConnectionPackage
	INITIATOR CONSUMER OF	{shadowConsumerPackage}
	ID					id-contract-shadowConsumer}
shadowSupplierContract  CONTRACT :: = {
	CONNECTION			dispConnectionPackage
	RESPONDER CONSUMER OF	{shadowSupplierPackage}
	ID					id-contract-shadowSupplier}

dispConnectionPackage  CONNECTION-PACKAGE::= {
	BIND		dSAShadowBind
	UNBIND	in-DSAShadowUnbind
	ID		id-package-dispConnection}

shadowConsumerPackage  OPERATION-PACKAGE :: = {
	CONSUMER INVOKES	{requestShadowUpdate}
	SUPPLIER INVOKES	{updateShadow}
	ID				id-package-shadowConsumer}
shadowSupplierPackage  OPERATION-PACKAGE :: = {
	SUPPLIER INVOKES	{coordinateShadowUpdate | updateShadow}
	ID				id-package-shadowSupplier}

inDirectorySystemAbstractSyntax  ABSTRACT-SYNTAX :: = {
	BasicDSP-PDUs
	IDENTIFIED BY		id-as-indirectorySystemAS}
BasicDSP-PDUs :: = TCMessage {{DSP-Invokable},{DSP-Returnable}}
DSP-Invokable OPERATION :: = {chainedAddEntry | chainedRemoveEntry | chainedModifyEntry | 
						chainedSearch | chainedExecute}
DSP-Returnable OPERATION :: = {chainedAddEntry | chainedRemoveEntry | chainedModifyEntry | 
						chainedSearch | chainedExecute}

inDirectoryDSABindingAbstractSyntax  ABSTRACT-SYNTAX :: = {
	DSABinding-PDUs
	IDENTIFIED BY		id-as-indirectoryDSABindingAS}
DSABinding-PDUs :: = CHOICE {
	bind		Bind {dSABind},
	unbind		Unbind {in-DSAUnbind}}

inDirectoryShadowAbstractSyntax ABSTRACT-SYNTAX :: = {
	BasicDISP-PDUs 
	IDENTIFIED BY		id-as-indirectoryShadowAS}
BasicDISP-PDUs :: = TCMessage {{DISP-Invokable},{DISP-Returnable}}
DISP-Invokable OPERATION :: ={requestShadowUpdate | updateShadow | coordinateShadowUpdate}
DISP-Returnable OPERATION :: ={requestShadowUpdate | updateShadow | coordinateShadowUpdate}

inDirectoryDSAShadowBindingAbstractSyntax  ABSTRACT-SYNTAX :: = {
	DISPBinding-PDUs
	IDENTIFIED BY		id-as-indsaShadowBindingAS}
DISPBinding-PDUs :: = CHOICE {
	bind 		Bind {dSAShadowBind},
	unbind	Unbind {in-DSAShadowUnbind}}

inDirectorySystemAC APPLICATION-CONTEXT :: = 	{
	CONTRACT			dspContract 
	DIALOGUE MODE		structured
	TERMINATION			basic
	ABSTRACT SYNTAXES		{dialogue-abstract-syntax |
							inDirectorySystemAbstractSyntax |
							inDirectoryDSABindingAbstractSyntax}
	APPLICATION CONTEXT NAME id-ac-indirectorySystemAC}

inDirectorySystemWith3seAC APPLICATION-CONTEXT :: = 	{
	CONTRACT			dspContract 
	DIALOGUE MODE		structured
	TERMINATION			basic
	ADDITIONAL ASE		{id-se-threewayse}
	ABSTRACT SYNTAXES	{dialogue-abstract-syntax |
						inDirectorySystemAbstractSyntax |
						inDirectoryDSABindingAbstractSyntax | 
						inSESEAbstractSyntax}
	APPLICATION CONTEXT NAME	id-ac-indirectorySystemWith3seAC}

inshadowSupplierInitiatedAC APPLICATION-CONTEXT :: = {
	CONTRACT					shadowSupplierContract
	DIALOGUE MODE				structured
	TERMINATION					basic
	ABSTRACT SYNTAXES			{dialogue-abstract-syntax |
								inDirectoryShadowAbstractSyntax |
								inDirectoryDSAShadowBindingAbstractSyntax}
	APPLICATION CONTEXT NAME	id-ac-inShadowSupplierInitiatedAC}

inshadowSupplierInitiatedWith3seAC APPLICATION-CONTEXT :: = {
	CONTRACT					shadowSupplierContract
	DIALOGUE MODE				structured
	TERMINATION					basic
	ADDITIONAL ASE				{id-se-threewayse} 
	ABSTRACT SYNTAXES			{dialogue-abstract-syntax |
								inDirectoryShadowAbstractSyntax |
								inDirectoryDSAShadowBindingAbstractSyntax | 
								inSESEAbstractSyntax}
	APPLICATION CONTEXT NAME	id-ac-inShadowSupplierInitiatedWith3seAC}

inshadowConsumerInitiatedAC APPLICATION-CONTEXT :: = {
	CONTRACT					shadowConsumerContract
	DIALOGUE MODE				structured
	TERMINATION					basic
	ABSTRACT SYNTAXES			{dialogue-abstract-syntax |
								inDirectoryShadowAbstractSyntax |
								inDirectoryDSAShadowBindingAbstractSyntax}
	APPLICATION CONTEXT NAME	id-ac-inShadowConsumerInitiatedAC}

inshadowConsumerInitiatedWith3seAC APPLICATION-CONTEXT :: = {
	CONTRACT					shadowConsumerContract
	DIALOGUE MODE				structured
	TERMINATION					basic
	ADDITIONAL ASE				{id-se-threewayse} 
	ABSTRACT SYNTAXES			{dialogue-abstract-syntax |
								inDirectoryShadowAbstractSyntax |
								inDirectoryDSAShadowBindingAbstractSyntax | 
								inSESEAbstractSyntax}
	APPLICATION CONTEXT NAME	id-ac-inShadowConsumerInitiatedWith3seAC}

IN-CS2-SDF-SDF-Protocol 
	{ ccitt recommendation q ccitt recommendation q 1228 module(0) in-cs2-sdf-sdf-Protocol(18) version1(0)} 

DEFINITIONS :: =

BEGIN 
-- EXPORTS All --
 
-- The types and values defined in this module are exported for use in the other ASN.1 modules
-- contained within the Directory Specifications, and for the use of other applications which will
-- use them to access Directory services. Other applications may use them for their own purposes,
-- but this will not constrain extensions and modifications needed to maintain or improve the
-- Directory service. 

IMPORTS 

distributedOperations, directoryShadowAbstractService, dsp, protocolObjectIdentifiers 
	FROM  UsefulDefinitions ds-UsefulDefinitions

ROS-OBJECT-CLASS, CONTRACT, OPERATION-PACKAGE, CONNECTION-PACKAGE, 
Code, OPERATION 
	FROM Remote-Operations-Information-Objects ros-InformationObjects

Bind{}, Unbind{}
	FROM Remote-Operations-Generic-ROS-PDUs ros-genericPDUs

TCMessage {}
	FROM TCAPMessages tc-Messages

APPLICATION-CONTEXT, dialogue-abstract-syntax
	FROM TC-Notation-Extensions tc-NotationExtensions

dSABind, 
chainedSearch, chainedAddEntry, chainedRemoveEntry, chainedModifyEntry, chained{}
	FROM DistributedOperations distributedOperations

dSAShadowBind, 
coordinateShadowUpdate, updateShadow, requestShadowUpdate
	FROM DirectoryShadowAbstractService directoryShadowAbstractService

execute 
	FROM IN-CS2-SCF-SDF-Operations scf-sdf-Operations

inEmptyUnbind
	FROM IN-CS2-classes {ccitt recommendation q ccitt recommendation q 1228 modules(0) 
																	in-cs2-classes(4) version1(0)}
id-rosObject-dspDSA, id-rosObject-initiatingConsumerDSA, id-rosObject-respondingSupplierDSA, 
id-rosObject-respondingConsumerDSA, id-rosObject-initiatingSupplierDSA, 
id-contract-indsp, id-contract-shadowConsumer, id-contract-shadowSupplier,
id-package-dspConnection, id-package-inchainedModify, id-package-inchainedSearch, 
id-package-chainedExecute, 
id-package-dispConnection, id-package-shadowConsumer, id-package-shadowSupplier, 
id-as-indirectorySystemAS, id-as-indirectoryDSABindingAS, id-as-indirectoryShadowAS, 
id-as-indsaShadowBindingAS, 
id-ac-indirectorySystemAC, id-ac-inShadowSupplierInitiatedAC, id-ac-inShadowConsumerInitiatedAC,
id-ac-inShadowSupplierInitiatedWith3seAC,id-ac-inShadowConsumerInitiatedWith3seAC,
id-ac-indirectorySystemWith3seAC,
ds-UsefulDefinitions, ros-InformationObjects, ros-genericPDUs, tc-Messages,
tc-NotationExtensions, scf-sdf-Operations, scf-sdf-Protocol 
	FROM IN-CS2-object-identifiers
		{ccitt recommendation q ccitt recommendation q 1228 module(0) in-cs2-object-identifiers(17) 
																						version1(0)}
inSESEAbstractSyntax
	FROM IN-CS2-SCF-SDF-Protocol scf-sdf-Protocol 

id-se-threewayse 
	FROM ProtocolObjectIdentifiers protocolObjectIdentifiers 

dspContract 
	FROM DirectorySystemProtocol dsp
; 

dsp-dsa  ROS-OBJECT-CLASS ::= {
	BOTH		{indspContract}
	ID			id-rosObject-dspDSA}

initiating-consumer-dsa  ROS-OBJECT-CLASS ::= {
	INITIATES		{shadowConsumerContract}
	ID				id-rosObject-initiatingConsumerDSA}

responding-supplier-dsa  ROS-OBJECT-CLASS ::= {
	RESPONDS		{shadowConsumerContract}
	ID				id-rosObject-respondingSupplierDSA}

initiating-supplier-dsa  ROS-OBJECT-CLASS ::= {
	INITIATES		{shadowSupplierContract}
	ID				id-rosObject-initiatingSupplierDSA}

responding-consumer-dsa  ROS-OBJECT-CLASS ::= {
	RESPONDS		{shadowSupplierContract}
	ID				id-rosObject-respondingConsumerDSA}

indspContract  CONTRACT ::= {
	CONNECTION		dspConnectionPackage
	INITIATOR CONSUMER OF	{inchainedModifyPackage | inchainedSearchPackage | 
						   chainedExecutePackage}
	ID				id-contract-indsp}

dspConnectionPackage  CONNECTION-PACKAGE ::= {
	BIND		dSABind
	UNBIND		in-DSAUnbind
	ID			id-package-dspConnection}

in-DSAUnbind	OPERATION ::= 	inEmptyUnbind

inchainedModifyPackage  OPERATION-PACKAGE ::= {
	CONSUMER INVOKES	{chainedAddEntry | chainedRemoveEntry | chainedModifyEntry}
	ID					id-package-inchainedModify}

inchainedSearchPackage OPERATION-PACKAGE ::= {
	CONSUMER INVOKES	{chainedSearch}
	ID					id-package-inchainedSearch}

chainedExecutePackage OPERATION-PACKAGE ::= {
	CONSUMER INVOKES	{chainedExecute}
	ID					id-package-chainedExecute}

chainedExecute	OPERATION ::= chained {execute}

shadowConsumerContract  CONTRACT ::= {
	CONNECTION			dispConnectionPackage
	INITIATOR CONSUMER OF	{shadowConsumerPackage}
	ID					id-contract-shadowConsumer}

shadowSupplierContract  CONTRACT ::= {
	CONNECTION			dispConnectionPackage
	RESPONDER CONSUMER OF	{shadowSupplierPackage}
	ID					id-contract-shadowSupplier}

dispConnectionPackage  CONNECTION-PACKAGE ::= {
	BIND		dSAShadowBind
	UNBIND		in-DSAShadowUnbind
	ID			id-package-dispConnection}

in-DSAShadowUnbind	OPERATION ::= 	inEmptyUnbind

shadowConsumerPackage  OPERATION-PACKAGE ::= {
	CONSUMER INVOKES	{requestShadowUpdate}
	SUPPLIER INVOKES	{updateShadow}
	ID					id-package-shadowConsumer}

shadowSupplierPackage  OPERATION-PACKAGE ::= {
	SUPPLIER INVOKES	{coordinateShadowUpdate | updateShadow}
	ID					id-package-shadowSupplier}

inDirectorySystemAbstractSyntax  ABSTRACT-SYNTAX ::= {
	BasicDSP-PDUs
	IDENTIFIED BY		id-as-indirectorySystemAS}

BasicDSP-PDUs :: = TCMessage {{DSP-Invokable},{DSP-Returnable}}

DSP-Invokable OPERATION ::= {chainedAddEntry | chainedRemoveEntry | chainedModifyEntry |
																chainedSearch | chainedExecute}

DSP-Returnable OPERATION ::= {chainedAddEntry | chainedRemoveEntry | chainedModifyEntry |
																chainedSearch | chainedExecute}

inDirectoryDSABindingAbstractSyntax  ABSTRACT-SYNTAX ::= {
	DSABinding-PDUs
	IDENTIFIED BY		id-as-indirectoryDSABindingAS}

DSABinding-PDUs :: = CHOICE {
	bind		Bind {dSABind},
	unbind		Unbind {in-DSAUnbind}}

inDirectoryShadowAbstractSyntax ABSTRACT-SYNTAX ::= {
	BasicDISP-PDUs 
	IDENTIFIED BY		id-as-indirectoryShadowAS}

BasicDISP-PDUs ::= TCMessage {{DISP-Invokable}, {DISP-Returnable}}

DISP-Invokable OPERATION ::= {requestShadowUpdate | updateShadow | coordinateShadowUpdate}

DISP-Returnable OPERATION ::= {requestShadowUpdate | updateShadow | coordinateShadowUpdate}

inDirectoryDSAShadowBindingAbstractSyntax  ABSTRACT-SYNTAX ::= {
	DISPBinding-PDUs
	IDENTIFIED BY		id-as-indsaShadowBindingAS}

DISPBinding-PDUs ::= CHOICE {
	bind 		Bind {dSAShadowBind},
	unbind		Unbind {in-DSAShadowUnbind}}

inDirectorySystemAC APPLICATION-CONTEXT ::= 	{
	CONTRACT				indspContract 
	DIALOGUE MODE			structured
	TERMINATION				basic
	ABSTRACT SYNTAXES		{dialogue-abstract-syntax |
							inDirectorySystemAbstractSyntax |
							inDirectoryDSABindingAbstractSyntax}
	APPLICATION CONTEXT NAME id-ac-indirectorySystemAC}

inDirectorySystemWith3seAC APPLICATION-CONTEXT ::= 	{
	CONTRACT				dspContract 
	DIALOGUE MODE			structured
	TERMINATION				basic
	ADDITIONAL ASE			{id-se-threewayse}
	ABSTRACT SYNTAXES		{dialogue-abstract-syntax |
							inDirectorySystemAbstractSyntax |
							inDirectoryDSABindingAbstractSyntax | 
							inSESEAbstractSyntax}
	APPLICATION CONTEXT NAME	id-ac-indirectorySystemWith3seAC}

inshadowSupplierInitiatedAC APPLICATION-CONTEXT ::= {
	CONTRACT				shadowSupplierContract
	DIALOGUE MODE			structured
	TERMINATION				basic
	ABSTRACT SYNTAXES		{dialogue-abstract-syntax |
							inDirectoryShadowAbstractSyntax |
							inDirectoryDSAShadowBindingAbstractSyntax}
	APPLICATION CONTEXT NAME	id-ac-inShadowSupplierInitiatedAC}

inshadowSupplierInitiatedWith3seAC APPLICATION-CONTEXT ::= {
	CONTRACT				shadowSupplierContract
	DIALOGUE MODE			structured
	TERMINATION				basic
	ADDITIONAL ASE			{id-se-threewayse} 
	ABSTRACT SYNTAXES		{dialogue-abstract-syntax |
							inDirectoryShadowAbstractSyntax |
							inDirectoryDSAShadowBindingAbstractSyntax | 
							inSESEAbstractSyntax}
	APPLICATION CONTEXT NAME	id-ac-inShadowSupplierInitiatedWith3seAC}

inshadowConsumerInitiatedAC APPLICATION-CONTEXT ::= {
	CONTRACT				shadowConsumerContract
	DIALOGUE MODE			structured
	TERMINATION				basic
	ABSTRACT SYNTAXES		{dialogue-abstract-syntax |
							inDirectoryShadowAbstractSyntax |
							inDirectoryDSAShadowBindingAbstractSyntax}
	APPLICATION CONTEXT NAME	id-ac-inShadowConsumerInitiatedAC}

inshadowConsumerInitiatedWith3seAC APPLICATION-CONTEXT ::= {
	CONTRACT				shadowConsumerContract
	DIALOGUE MODE			structured
	TERMINATION				basic
	ADDITIONAL ASE			{id-se-threewayse} 
	ABSTRACT SYNTAXES		{dialogue-abstract-syntax |
							inDirectoryShadowAbstractSyntax |
							inDirectoryDSAShadowBindingAbstractSyntax | 
							inSESEAbstractSyntax}
	APPLICATION CONTEXT NAME	id-ac-inShadowConsumerInitiatedWith3seAC}

END

IN-CS2-SCF-SCF-ops-args {ccitt recommendation q 1228 modules(0) in-cs2-scf-scf-ops-args (13) version1(0)}

-- The profiling of Directory Operations Parameters for the SCF-SCF relationship is outside the 
-- scope of IN CS2. Optional parameters received but not used in the SCF-SCF case are ignored. 
-- Appropriate parameters to be used should be establish via agreement ahead of time.

DEFINITIONS IMPLICIT TAGS  ::=
BEGIN

IMPORTS
	OPERATION, Code, ERROR
FROM Remote-Operations-Information-Objects ros-InformationObjects

	SecurityParameters,
	Credentials,
	SecurityProblem,
	securityError
FROM DirectoryAbstractService directoryAbstractService

	OPTIONALLY-PROTECTED{}
FROM EnhancedSecurity enhancedSecurity

	PROTECTION-MAPPING
FROM Notation guls-Notation

	AccessPointInformation
FROM DistributedOperations distributedOperations

	opcode-establishChargingRecord,
	opcode-handlingInformationRequest,
	opcode-handlingInformationResult,
	opcode-networkCapability,
	opcode-notificationProvided,
	opcode-confirmedNotificationProvided,
	opcode-provideUserInformation,
	opcode-confirmedReportChargingInformation,
	opcode-reportChargingInformation,
	opcode-requestNotification
FROM IN-CS2-operationcodes operationcodes

	EXTENSION,
	PARAMETERS-BOUND,
	SupportedExtensions {}
FROM IN-CS2-classes 

	AccountNumber,
	ActivableServices,
	BearerCapabilities,
	BearerCapability {},
	CallConditions {},
	CalledPartyNumber {},
	CallingPartyNumber {},
	CallingPartysCategory, 
	CallRecord {},
	Carrier,
	Cause {},
	ChargingParameters {},
	Digits {},
	DisplayInformation {},
	ErrorTreatment,
	ExtensionField {},
	HighLayerCompatibilities,
	HighLayerCompatibility,
	InfoToSend {},
	InfoType,
	Integer4,
	InteractionStrategy,
	InvokableService,
	Language,
	LocationNumber {},
	Notification,
	NotificationInformation {},
	NumberMatch {},
	OriginalCalledPartyID {},
	ReceivedInformation {},
	RedirectingPartyID {},
	RedirectionInformation,
	RequestedNotifications {},
	RequestedType,
	RoutingAddress {},
	ScfAddress {},
	ScfID {},
	SubscriberId {},
	SupplementaryServices,
	ToneId,
	TraceInformation{},
	TraceItem{},
	UnavailableNetworkResource,
	UserCredit {},
	UserInfo {},
	UserInformation {},
	UserInteractionModes
FROM IN-CS2-datatypes datatypes

	improperCallerResponse,
	missingCustomerRecord,
	missingParameter,
	parameterOutOfRange,
	systemFailure,
	unexpectedComponentSequence,
	unexpectedDataValue,
	unexpectedParameter,
	chainingRefused
FROM IN-CS2-errortypes errortypes

	errcode-scfReferral,
	errcode-scfTaskRefused
FROM IN-CS2-errorcodes errorcodes

	AuthenticationLevel
FROM BasicAccessControl basicAccessControl

	SPKM-ERROR
FROM SpkmGssTokens spkmGssTokens

	activityTest
FROM IN-CS2-SSF-SCF-ops-args ssf-scf-Operations

	ros-InformationObjects, ds-UsefulDefinitions,  operationcodes,
	classes, guls-Notation, guls-SecurityTransformations, errortypes, errorcodes,
	scf-scf-Protocol, ssf-scf-Operations, datatypes, spkmGssTokens
FROM IN-CS2-object-identifiers {ccitt recommendation q 1228 modules(0) in-cs2-object-identifiers(17) version1(0)}

	directoryAbstractService, enhancedSecurity, distributedOperations, basicAccessControl
FROM UsefulDefinitions ds-UsefulDefinitions
;

establishChargingRecord {PARAMETERS-BOUND : bound}  OPERATION  ::= {
	ARGUMENT		EstablishChargingRecordArg {bound}
	RETURN RESULT	FALSE
	ERRORS			{missingCustomerRecord |
					missingParameter |
					systemFailure |
					scfTaskRefused |
					unexpectedComponentSequence |
					unexpectedDataValue |
					unexpectedParameter |
					parameterOutOfRange|
					securityError
					}
	CODE			opcode-establishChargingRecord
	}
-- Direction: supporting SCF --> controlling SCF, Timer Tecr
-- This operation is used by the supporting SCF to give charging information to the controlling 
-- SCF so that it can charge the user (on-line charging included).

EstablishChargingRecordArg  {PARAMETERS-BOUND : bound}  ::= OPTIONALLY-PROTECTED {SEQUENCE {
	userCredit			[0] UserCredit {bound}	OPTIONAL,
	chargingParameters	[1] ChargingParameters {bound}	OPTIONAL,
	reportExpected		[2] BOOLEAN  	DEFAULT TRUE,
	securityParameters	[3] SecurityParameters	OPTIONAL,
	extensions			[4] SEQUENCE SIZE (1..bound.&numOfExtensions) OF	
																ExtensionField {bound}	OPTIONAL,
	...
	},
	SCFQOP.&scfArgumentQOP{@scfqop}
	}

handlingInformationRequest {PARAMETERS-BOUND : bound}  OPERATION  ::= {
	ARGUMENT		HandlingInformationRequestArg {bound}
	RETURN RESULT	FALSE
	ERRORS			{missingCustomerRecord |
					missingParameter |
					parameterOutOfRange |
					systemFailure |
					scfTaskRefused |
					unexpectedComponentSequence |
					unexpectedDataValue |
					unexpectedParameter |
					securityError |
					scfReferral
					}
	LINKED			{handlingInformationResult {bound}}
	CODE			opcode-handlingInformationRequest
	}
-- Direction: controlling SCF --> supporting SCF (or IAF), Timer Thi
-- This operation  may be used   request the  execution of an SLP 
-- in the assisting SCF and to provide to the  assisting
-- SCF the context of the call so that it can help the  controlling SCF in the processing of the 
-- call.

HandlingInformationRequestArg {PARAMETERS-BOUND : bound}  ::= OPTIONALLY-PROTECTED {SEQUENCE {
	requestedType				[0] RequestedType					OPTIONAL,
	callingPartyNumber			[1] CallingPartyNumber {bound}		OPTIONAL,
	locationNumber				[2] LocationNumber {bound}			OPTIONAL,
	calledPartyNumber			[3] CalledPartyNumber {bound}		OPTIONAL,
	dialledDigits				[4] Digits {bound}					OPTIONAL,
	redirectingPartyID			[5] RedirectingPartyID {bound}		OPTIONAL,
	redirectionInformation		[6] RedirectionInformation			OPTIONAL,
	originalCalledPartyID		[7] OriginalCalledPartyID {bound}	OPTIONAL,
	numberOfCallAttempts		[8] INTEGER (1..bound.&ub-nbCall) 	OPTIONAL,
	highLayerCompatibility		[9] HighLayerCompatibility 			OPTIONAL,
	bearerCapability			[10] BearerCapability {bound}		OPTIONAL,
	invokedSupplementaryService	[11] InvokableService 				OPTIONAL,
	activeSupplementaryServices	[12] ActivableServices 				OPTIONAL,
	causeOfLastCallFailure		[13] Cause {bound}					OPTIONAL,
	userInteractionModes		[14] UserInteractionModes 			OPTIONAL,
	callingPartysCategory		[15] CallingPartysCategory 			OPTIONAL,
	callingPartyBusinessGroupID	[16] OCTET STRING					OPTIONAL,
	securityParameters			[17] SecurityParameters				OPTIONAL,
	extensions					[18] SEQUENCE SIZE (1..bound.&numOfExtensions)
										OF ExtensionField {bound}	OPTIONAL,
	...
	},
	SCFQOP.&scfArgumentQOP{@scfqop}
	}

handlingInformationResult {PARAMETERS-BOUND : bound}  OPERATION  ::= {
	ARGUMENT			HandlingInformationResultArg {bound}
	RETURN RESULT		FALSE
	ERRORS				{missingParameter |
						systemFailure |
						parameterOutOfRange |
						unexpectedComponentSequence |
						unexpectedDataValue |
						unexpectedParameter |
						securityError
						}
	CODE				opcode-handlingInformationResult
	}
-- Direction: supporting SCF(or IAF) -->controlling SCF, Timer Thir
-- This operation is used by the assisting SCF to send information to the  controlling SCF on how 
-- to process the call and to give conditions under which it should be involved in the call 
-- processing.

HandlingInformationResultArg {PARAMETERS-BOUND : bound}  ::= OPTIONALLY-PROTECTED {SEQUENCE {
	routingAddress			[0] RoutingAddress {bound}			OPTIONAL,
	highLayerCompatibility	[1] HighLayerCompatibility			OPTIONAL,
	supplementaryServices	[2] SupplementaryServices			OPTIONAL,
	preferredLanguage		[3] Language 						OPTIONAL,
	carrier					[4] Carrier 						OPTIONAL,
	callingPartyNumber		[5] CallingPartyNumber {bound} 		OPTIONAL,
	originalCalledPartyID	[6] OriginalCalledPartyID  {bound}	OPTIONAL,
	redirectingPartyID		[7] RedirectingPartyID  {bound}		OPTIONAL,
	redirectionInformation	[8] RedirectionInformation 			OPTIONAL,
	callingPartysCategory	[9] CallingPartysCategory 			OPTIONAL,
	securityParameters		[10] SecurityParameters				OPTIONAL,
	extensions				[11] SEQUENCE SIZE (1..bound.&numOfExtensions) OF ExtensionField {bound}
																OPTIONAL,
	...
	},
	SCFQOP.&scfArgumentQOP{@scfqop}
	}


networkCapability  {PARAMETERS-BOUND : bound}  OPERATION  ::= {
	ARGUMENT		NetworkCapabilityArg {bound}
	RESULT			NetworkCapabilityResultArg {bound}
	ERRORS			{missingCustomerRecord |
					missingParameter |
					systemFailure |
					scfTaskRefused |
					unexpectedComponentSequence |
					unexpectedDataValue |
					unexpectedParameter |
					securityError
					}
	CODE			opcode-networkCapability
	}
-- Direction: supporting SCF -->controlling  SCF, Timer Tnc
-- This operation is used by the supporting SCF to request from the controlling SCF which type of 
-- service it supports.

NetworkCapabilityArg  {PARAMETERS-BOUND : bound}  ::= OPTIONALLY-PROTECTED {SEQUENCE {
	bearerCapabilities			[0] BearerCapabilities 				OPTIONAL,
	highLayerCompatibilities	[1] HighLayerCompatibilities		OPTIONAL,
	supplementaryServices		[2] SupplementaryServices 			OPTIONAL,
	securityParameters			[3] SecurityParameters				OPTIONAL,
	extensions					[4] SEQUENCE SIZE (1..bound.&numOfExtensions) OF 
										ExtensionField {bound}		OPTIONAL,
	...
	},
	SCFQOP.&scfArgumentQOP{@scfqop}
	}

NetworkCapabilityResultArg  {PARAMETERS-BOUND : bound}  ::= OPTIONALLY-PROTECTED {SEQUENCE {
	bearerCapabilities			[0] BearerCapabilities 				OPTIONAL,
	highLayerCompatibilities	[1] HighLayerCompatibilities 		OPTIONAL,
	supplementaryServices		[2] SupplementaryServices 			OPTIONAL,
	securityParameters			[3] SecurityParameters				OPTIONAL,
	extensions					[4] SEQUENCE SIZE (1..bound.&numOfExtensions) OF
											ExtensionField {bound}	OPTIONAL,
	...
	},
	SCFQOP.&scfArgumentQOP{@scfqop}
	}

notificationProvided  {PARAMETERS-BOUND : bound}   OPERATION  ::= {
	ARGUMENT			NotificationProvidedArg {bound}
	RETURN RESULT		FALSE
	ERRORS				{missingParameter |
						systemFailure |
						scfTaskRefused |
						unexpectedComponentSequence |
						unexpectedDataValue |
						unexpectedParameter|
						missingCustomerRecord |
						parameterOutOfRange |
						securityError
						}
		CODE			opcode-notificationProvided
	}
-- Direction: controlling SCF --> supporting SCF(or IAF), Timer Tnp
-- This operation is used by the controlling SCF to request assistance from the assisting SCF 
-- under specific call conditions specified prior to the sending of the operation or to notify the 
-- outcome of a previous intervention of the assisting SCF.

NotificationProvidedArg {PARAMETERS-BOUND : bound}  ::= OPTIONALLY-PROTECTED {SEQUENCE {
	notification			[0] Notification, 
	notificationInformation	[1] NotificationInformation {bound}		OPTIONAL, 
	securityParameters		[2] SecurityParameters					OPTIONAL,
	extensions				[3] SEQUENCE SIZE (1..bound.&numOfExtensions) 
										OF ExtensionField {bound}	OPTIONAL,
	...
	},
	SCFQOP.&scfArgumentQOP{@scfqop}
	}

confirmedNotificationProvided {PARAMETERS-BOUND : bound} OPERATION  ::= makeConfirm {
	notificationProvided{bound},
	opcode-confirmedNotificationProvided}

--Direction: controlling SCF -->supporting SCF, Timer Thinc

provideUserInformation  {PARAMETERS-BOUND : bound}   OPERATION  ::= {
	ARGUMENT			ProvideUserInformationArg {bound}
	RESULT				ProvideUserInformationResultArg {bound}
	ERRORS				{missingCustomerRecord |
						missingParameter |
						systemFailure |
						scfTaskRefused |
						unexpectedComponentSequence |
						unexpectedDataValue |
						unexpectedParameter |
						improperCallerResponse |
						parameterOutOfRange |
						securityError
						}
	CODE				opcode-provideUserInformation
	}
-- Direction: supporting SCF --> controlling SCF, Timer Tpui
-- This operation is used by the supporting SCF to request information from the user that can be 
-- interrogated by the controlling SCF.

ProvideUserInformationArg  {PARAMETERS-BOUND : bound}  ::= OPTIONALLY-PROTECTED {SEQUENCE {
	constraints				[0] CollectedInfo, 
	infoToSend				[1] InformationToSend {bound}, 
	errorInfo				[2] InformationToSend {bound}			OPTIONAL, 
	typeOfRequestedInfo		[3] InfoType							DEFAULT numericString, 
	numberOfAllowedRetries 	[4] INTEGER (0.. 127)					DEFAULT	0, 
	actions					[5] Actions								OPTIONAL, 
	preferredLanguage		[6] Language							OPTIONAL, 
	securityParameters		[7] SecurityParameters					OPTIONAL,
	extensions				[8] SEQUENCE SIZE (1.. bound.&numOfExtensions) 
										OF ExtensionField {bound}	OPTIONAL,
	...
	},
	SCFQOP.&scfArgumentQOP{@scfqop}
	}

CollectedInfo  ::= CHOICE {
	collectedDigits	[0] CollectedDigits, 
	iA5Information	[1] BOOLEAN
}


CollectedDigits  ::= SEQUENCE {
	minimumNbOfDigits	[0] INTEGER (1.. 127)				DEFAULT 1, 
	maximumNbOfDigits	[1] INTEGER (1.. 127), 
	endOfReplyDigit		[2] IA5String (SIZE (1) )			OPTIONAL, 
	cancelDigit	 		[3] IA5String (SIZE (1) )			OPTIONAL, 
	startDigit	 		[4] IA5String (SIZE (1) )			OPTIONAL, 
	firstDigitTimeOut	[5] INTEGER (1.. 127)				OPTIONAL, 
	interDigitTimeOut	[6] INTEGER (1.. 127)				OPTIONAL, 
	errorTreatment		[7] ErrorTreatment					DEFAULT reportErrorToScf, 
	interruptableAnnInd	[8] BOOLEAN							DEFAULT TRUE, 
	voiceInformation	[9] BOOLEAN							DEFAULT FALSE, 
	voiceBack			[10] BOOLEAN						DEFAULT FALSE,
	...
	}


InformationToSend {PARAMETERS-BOUND}  ::= CHOICE {
	inbandInfo	 		[0] InbandInfo, 
	tone	 			[1] Tone, 
	displayInformation	[2] DisplayInformation{bound}
	}


InbandInfo  ::= SEQUENCE {
	messageId			[0] MessageID, 
	numberOfRepetitions	[1] INTEGER (1..127)			OPTIONAL, 
	duration			[2] INTEGER (1..32767)			OPTIONAL, 
	interval			[3] INTEGER (1..32767) 			OPTIONAL,
	...
	}


Tone  ::= SEQUENCE {
	toneId	 			[0] Integer4, 
	duration			[1] Integer4					OPTIONAL,
	...
	}


Actions  ::= ENUMERATED {
	play (0), 
	playandcollect (1) 
	}


MessageID  ::= OBJECT IDENTIFIER


ProvideUserInformationResultArg   {PARAMETERS-BOUND : bound}
 ::= OPTIONALLY-PROTECTED {SEQUENCE {
	userInformation		[0] ReceivedInformation {bound},
	securityParameters	[1] SecurityParameters			OPTIONAL,
	extensions			[1] SEQUENCE SIZE (1..bound.&numOfExtensions) OF ExtensionField {bound}
																							OPTIONAL
	},
	...
	SCFQOP.&scfArgumentQOP{@scfqop}
	}


reportChargingInformation   {PARAMETERS-BOUND : bound} OPERATION  ::= {
	ARGUMENT	ReportChargingInformationArg {bound}
	RETURN RESULT				FALSE
	ERRORS						{missingCustomerRecord |
								missingParameter |
								systemFailure |
								scfTaskRefused |
								unexpectedComponentSequence |
								unexpectedDataValue |
								unexpectedParameter |
								parameterOutOfRange |
								securityError
								}
	CODE						opcode-reportChargingInformation
	}
-- Direction: controlling SCF --> supporting SCF, Timer Trci
-- This operation is used to give to the assisting network charging information collected by the 
-- controlling network.



ReportChargingInformationArg   {PARAMETERS-BOUND : bound}  ::= OPTIONALLY-PROTECTED {SEQUENCE {
	callRecord			[0] CallRecord {bound}					OPTIONAL, 
	remainingUserCredit	[1] UserCredit {bound}					OPTIONAL, 
	uniqueCallID 		[2] CallIdentifier  					OPTIONAL, 
	accountNumber		[3] AccountNumber						OPTIONAL,
	securityParameters	[4] SecurityParameters					OPTIONAL
	},
	...
	SCFQOP.&scfArgumentQOP{@scfqop}
	}

CallIdentifier  ::= Integer4


confirmedReportChargingInformation {PARAMETERS-BOUND : bound} OPERATION  ::= makeConfirm {
	reportChargingInformation{bound},
	opcode-confirmedReportChargingInformation
	}
-- Direction: controlling SCF --> supporting SCF, Timer Trcic

requestNotification    {PARAMETERS-BOUND : bound}  OPERATION  ::= {
	ARGUMENT		RequestNotificationArg {bound}
	RETURN RESULT	FALSE
	ERRORS			{missingParameter|
					systemFailure|
					scfTaskRefused|
					unexpectedComponentSequence|
					unexpectedDataValue|
					unexpectedParameter|
					parameterOutOfRange|
					missingCustomerRecord|
					securityError
					}
	CODE			opcode-requestNotification
	}

--  Direction: supporting SCF  (or IAF) --> controlling SCF, Timer Trn
-- This operation is used by the assisting SCF to request notification from the controlling SCF 
-- under specific call conditions specified by this operation.


RequestNotificationArg    {PARAMETERS-BOUND : bound}  ::= OPTIONALLY-PROTECTED {SEQUENCE {
	requestedNotifications	[0] RequestedNotifications {bound},
	securityParameters		[1] SecurityParameters				OPTIONAL
	},
	...
	SCFQOP.&scfArgumentQOP{@scfqop}
	}



scfBind {PARAMETERS-BOUND : bound} OPERATION  ::= {
	ARGUMENT			SCFBindArgument{bound}
	RESULT				SCFBindResult {bound}
	ERRORS				{scfBindFailure}
	}

-- Direction: controlling SCF --> assisting SCF (or IAF) Timer Tbi
-- This operation is used to establish a relationship between two SCFs. It sent by the controlling  
-- SCF each time it needs to initiate communications with another (supporting) SCF. 

SCFBindArgument  {PARAMETERS-BOUND : bound}  ::= SEQUENCE {
	agreementID				[0] AgreementID,
	originatingScfAddress	[1] ScfAddress {bound}				OPTIONAL,
-- absent in a chained operation request which crosses an international internetworking boundary
	credentials				[2] Credentials						OPTIONAL,
	...
	}


SCFBindResult  {PARAMETERS-BOUND : bound}  ::= SEQUENCE {
	respondingScfAddress	[0] ScfAddress {bound} 				OPTIONAL,
-- absent in a chained operation request which crosses an international internetworking boundary
	returnedCredentials		[1] Credentials						OPTIONAL,
	...
	}


AgreementID  ::= OBJECT IDENTIFIER




scfUnbind OPERATION  ::=  {
RETURN RESULT 			FALSE
ALWAYS RESPONDS			FALSE
}
-- Direction: controlling SCF --> assisting SCF (or IAF) 
-- The SCF Unbind operation is used by the controlling SCF to close the relationship with the 
-- supporting SCF. 

scfChained  {OPERATION: operation, PARAMETERS-BOUND : bound}  OPERATION  ::= {
	ARGUMENT	OPTIONALLY-PROTECTED {SEQUENCE {
			chainedArgument	ChainingArgument {bound},
			argument			[0] operation.&ArgumentType				OPTIONAL
			},
			...
			SCFQOP.&scfArgumentQOP{@scfqop}
			}
	RESULT	OPTIONALLY-PROTECTED {SEQUENCE  {
			chainedResult	ChainingResult {bound},
			result				[0]operation.&ResultType				OPTIONAL
			},
			...
			SCFQOP.&scfArgumentQOP{@scfqop}
			}
	ERRORS	{operation.&Errors |
			chainingRefused |
			securityError |
			scfReferral
			}
	CODE	operation.&operationCode
	}

ChainingArgument    {PARAMETERS-BOUND : bound}  ::= SEQUENCE  {
	originatingSCF			[0] ScfID {bound},
	target					[1] SubscriberId {bound}					OPTIONAL,
	traceInformation		[2] TraceInformation{bound},
	scfAuthenticationLevel	[3] AuthenticationLevel 			DEFAULT  basicLevels: {level none},
	timeLimit				[4] UTCTime 								OPTIONAL,
	securityParameters		[5] SecurityParameters 						OPTIONAL, 
	extensions				[6] SEQUENCE SIZE (1..bound.&numOfExtensions)
								OF ExtensionField {bound}				OPTIONAL,
	...
	}

ChainingResult    {PARAMETERS-BOUND : bound}  ::= SEQUENCE  {
	ultimateResponder	[0] ScfAddress {bound} 							OPTIONAL,
	traceInformation	[1] TraceInformation{bound},
	securityParameters	[2] SecurityParameters							OPTIONAL,
	extensions			[3] SEQUENCE SIZE (1..bound.&numOfExtensions) OF ExtensionField {bound}
																		OPTIONAL,
	...
	}


makeConfirm {OPERATION: operation, Code: code} OPERATION  ::= {
	&ArgumentType			operation.&ArgumentType						OPTIONAL,
	&argumentTypeOptional	operation.&argumentTypeOptional OPTIONAL, 
	&ResultType				NULL,
	&Errors	operation.&Errors											OPTIONAL,
	&alwaysReturns			BOOLEAN TRUE,
	&operationCode	code}


chainedEstablishChargingRecord   {PARAMETERS-BOUND : bound}  OPERATION  ::= 
													scfChained{establishChargingRecord{bound},bound}

chainedHandlingInformationRequest {PARAMETERS-BOUND : bound} OPERATION  ::= 
												scfChained {handlingInformationRequest{bound},bound}

chainedHandlingInformationResult {PARAMETERS-BOUND : bound} OPERATION  ::= 
											scfChained{handlingInformationResult{bound},bound}

chainedNetworkCapability {PARAMETERS-BOUND : bound}   OPERATION  ::= 
											scfChained {networkCapability{bound},bound}

chainedNotificationProvided {PARAMETERS-BOUND : bound} OPERATION  ::= 
											scfChained {notificationProvided{bound},bound}

chainedConfirmedNotificationProvided {PARAMETERS-BOUND : bound} OPERATION  ::= 
											scfChained {confirmedNotificationProvided {bound},bound}

chainedProvideUserInformation {PARAMETERS-BOUND : bound} OPERATION  ::= 
											scfChained {provideUserInformation{bound},bound}

chainedReportChargingInformation {PARAMETERS-BOUND : bound} OPERATION  ::= 
											scfChained {reportChargingInformation{bound},bound}

chainedConfirmedReportChargingInformation {PARAMETERS-BOUND : bound} OPERATION  ::=
										scfChained{confirmedReportChargingInformation{bound}, bound}

chainedRequestNotification {PARAMETERS-BOUND : bound} OPERATION  ::=
											scfChained{requestNotification{bound}, bound}


SCFQOP  ::= CLASS {
	&scfqop-id			OBJECT IDENTIFIER UNIQUE,
	&scfBindErrorQOP	PROTECTION-MAPPING,
	&scfErrorsQOP		PROTECTION-MAPPING,
	&scfArgumentQOP		PROTECTION-MAPPING,
	&scfResultQOP		PROTECTION-MAPPING 
	}
WITH SYNTAX {
	SCFQOP-ID			&scfqop-id,
	SCFBINDERROR-QOP	&scfBindErrorQOP,
	SCFERRORS-QOP		&scfErrorsQOP,
	SCFOPARG-QOP		&scfArgumentQOP,
	SCFOPRES-QOP		&scfResultQOP
	}


scfBindFailure ERROR  ::= {
	PARAMETER			FailureReason
	}


FailureReason  ::= CHOICE {
	systemFailure		[0] UnavailableNetworkResource,
	scfTaskRefused 		[1] ScfTaskRefusedParameter,
	securityError 		[2] SET {
			problem 		[0] SecurityProblem,
			spkmInfo		[1] SPKM-ERROR
			}
	}

scfTaskRefused ERROR  ::= {
	PARAMETER	ScfTaskRefusedParameter
	CODE		errcode-scfTaskRefused
	}


ScfTaskRefusedParameter  ::= OPTIONALLY-PROTECTED {SEQUENCE {
		reason	ENUMERATED {
			generic(0),
			unobtainable (1),
			congestion(2)
			--other values FOR FURTHER STUDY
			},
		securityParameters	[1] SecurityParameters			OPTIONAL,
		...
	},
	SCFQOP.&scfErrorsQOP{@scfqop}
	}

scfReferral ERROR  ::= {
	PARAMETER	ReferralParameter
	CODE		errcode-scfReferral
	}


ReferralParameter  ::= OPTIONALLY-PROTECTED {
	SEQUENCE {
		tryhere				[0] AccessPointInformation,
		securityParameters	[1] SecurityParameters			OPTIONAL 
		},
	SCFQOP.&scfErrorsQOP{@scfqop},
	...
	}


END


-- This section includes all of the ASN.1 type and value definitions contained in this SCF/SCF  
-- Specification, in the form of the ASN.1 module, "IN-CS2-SCF-SCF-pkgs-contracts-acs".

IN-CS2-SCF-SCF-pkgs-contracts-acs {ccitt recommendation q 1228 modules(0) in-cs2-scf-scf-pkgs-contracts-acs (14) version1(0)} 

DEFINITIONS  ::=
BEGIN 

-- This module describes the operation-packages, contracts and application-contexts used
-- over the SCF-SCF interface.

IMPORTS 

	PARAMETERS-BOUND,
	networkSpecificBoundSet
FROM IN-CS2-classes classes

	ROS-OBJECT-CLASS, CONTRACT, OPERATION-PACKAGE, CONNECTION-PACKAGE, OPERATION
FROM Remote-Operations-Information-Objects ros-InformationObjects

	Bind{}, Unbind{}
FROM Remote-Operations-Generic-ROS-PDUs ros-genericPDUs 

	TCMessage {}
FROM  TCAPMessages tc-Messages

	APPLICATION-CONTEXT, dialogue-abstract-syntax
FROM TC-Notation-Extensions tc-NotationExtensions

	establishChargingRecord {},
	confirmedReportChargingInformation{},
	confirmedNotificationProvided {},
	handlingInformationRequest {},
	handlingInformationResult {},
	networkCapability {},
	notificationProvided {},
	provideUserInformation {},
	reportChargingInformation {},
	requestNotification {},
	chainedHandlingInformationRequest {},
	chainedNotificationProvided {},
	chainedConfirmedNotificationProvided {},
	chainedReportChargingInformation {},
	chainedConfirmedReportChargingInformation{},
	chainedEstablishChargingRecord {},
	chainedHandlingInformationResult {},
	chainedNetworkCapability {},
	chainedProvideUserInformation {},
	chainedRequestNotification {},
	scfBind{},
	scfUnbind
FROM IN-CS2-SCF-SCF-ops-args scf-scf-Operations

	id-ac,
	id-rosObject,
	id-contract,
	id-package,
	id-as,
	id-ac-scf-scfOperationsAC,
	id-ac-distributedSCFSystemAC,
	id-ac-scf-scfOperationsWith3seAC,
	id-ac-distributedSCFSystemWith3seAC,
	id-contract-scf-scf,
	id-contract-dssp,
	id-package-dsspConnection, 
	id-package-scf-scfConnection,
	id-package-handlingInformation,
	id-package-notification,
	id-package-chargingInformation,
	id-package-userInformation,
	id-package-networkCapability,
	id-package-chainedSCFOperations,
	id-as-scf-scfOperationsAS,
	id-as-distributedSCFSystemAS,
	id-as-scf-scfBindingAS,
	ds-UsefulDefinitions,
	classes, 
	tc-Messages, tc-NotationExtensions,
	ros-InformationObjects, ros-genericPDUs,
	scf-scf-Operations, scf-sdf-Protocol,
	ssf-scf-Operations, ssf-scf-Protocol 
FROM IN-CS2-object-identifiers {ccitt recommendation q 1228 modules(0) in-cs2-object-identifiers (17) version1(0)}

	activityTest
FROM IN-CS2-SSF-SCF-ops-args ssf-scf-Operations

	activityTestPackage
FROM IN-CS2-SSF-SCF-pkgs-contracts-acs ssf-scf-Protocol

	inSESEAbstractSyntax
FROM IN-CS2-SCF-SDF-Protocol scf-sdf-Protocol 

	id-se-threewayse 
FROM ProtocolObjectIdentifiers protocolObjectIdentifiers 

	protocolObjectIdentifiers 
FROM UsefulDefinitions ds-UsefulDefinitions
; 


-- Application Contexts -- 

scf-scfOperationsAC  APPLICATION-CONTEXT  ::= {
	CONTRACT					scf-scfContract 
	DIALOGUE MODE				structured
	TERMINATION					basic
	ABSTRACT SYNTAXES			{dialogue-abstract-syntax |
								distributedSCFBindingAbstractSyntax |
								scf-scfOperationsAbstractSyntax}
	APPLICATION CONTEXT NAME	id-ac-scf-scfOperationsAC
	}

distributedSCFSystemAC  APPLICATION-CONTEXT  ::= {
	CONTRACT					dsspContract
	DIALOGUE MODE				structured
	TERMINATION					basic
	ABSTRACT SYNTAXES			{dialogue-abstract-syntax |
								distributedSCFSystemAbstractSyntax |
								distributedSCFBindingAbstractSyntax}
	APPLICATION CONTEXT NAME	id-ac-distributedSCFSystemAC
	}

scf-scfOperationsWith3seAC  APPLICATION-CONTEXT  ::= {
	CONTRACT					scf-scfContract 
	DIALOGUE MODE				structured
	TERMINATION					basic
	ADDITIONAL ASE				{id-se-threewayse} 
	ABSTRACT SYNTAXES			{dialogue-abstract-syntax |
								distributedSCFBindingAbstractSyntax |
								scf-scfOperationsAbstractSyntax |
								inSESEAbstractSyntax}
	APPLICATION CONTEXT NAME	id-ac-scf-scfOperationsWith3seAC
	}

distributedSCFSystemWith3seAC  APPLICATION-CONTEXT  ::= {
	CONTRACT					dsspContract
	DIALOGUE MODE				structured
	TERMINATION					basic
	ADDITIONAL ASE				{id-se-threewayse}
	ABSTRACT SYNTAXES			{dialogue-abstract-syntax |
								distributedSCFSystemAbstractSyntax |
								distributedSCFBindingAbstractSyntax |
								inSESEAbstractSyntax}
	APPLICATION CONTEXT NAME	id-ac-distributedSCFSystemWith3seAC
	}

-- Contracts --

scf-scfContract  CONTRACT  ::= {
	CONNECTION					scf-scfConnectionPackage{networkSpecificBoundSet}
	INITIATOR CONSUMER OF		{activityTestPackage |
								handlingInformationPackage
{networkSpecificBoundSet}
								}
	RESPONDER CONSUMER OF		{activityTestPackage |
								chargingInformationPackage
{networkSpecificBoundSet}| 		networkCapabilityPackage
{networkSpecificBoundSet}|		notificationPackage
{networkSpecificBoundSet}| 		userInformationPackage
{networkSpecificBoundSet} 		}
	ID							id-contract-scf-scf
	}

dsspContract  CONTRACT  ::= {
	CONNECTION	dsspConnectionPackage {networkSpecificBoundSet}
	INITIATOR CONSUMER OF	{chainedSCFOperationPackage{networkSpecificBoundSet}}
	ID							id-contract-dssp
	}

-- Connection Package --

scf-scfConnectionPackage {PARAMETERS-BOUND : bound} CONNECTION-PACKAGE  ::= {
	BIND				scfBind{bound}
	UNBIND				scfUnbind
	RESPONDER UNBIND	FALSE
	ID					id-package-scf-scfConnection
	}

dsspConnectionPackage {PARAMETERS-BOUND : bound} CONNECTION-PACKAGE  ::= {
	BIND				scfBind{bound}
	UNBIND				scfUnbind
	RESPONDER UNBIND	FALSE
	ID					id-package-dsspConnection
	}

--  handlingInformation package --

handlingInformationPackage  {PARAMETERS-BOUND : bound}   OPERATION-PACKAGE  ::= {
	CONSUMER INVOKES	{handlingInformationRequest {bound}}
	SUPPLIER INVOKES	{handlingInformationResult {bound}}
	ID					id-package-handlingInformation
	}

--  notification package --

notificationPackage  {PARAMETERS-BOUND : bound}   OPERATION-PACKAGE  ::= {
	CONSUMER INVOKES	{requestNotification {bound}}
	SUPPLIER INVOKES	{notificationProvided {bound}| confirmedNotificationProvided}
	ID					id-package-notification
	}

--  chargingInformation package --

chargingInformationPackage  {PARAMETERS-BOUND : bound}   OPERATION-PACKAGE  ::= {
	CONSUMER INVOKES	{establishChargingRecord {bound}}
	SUPPLIER INVOKES	{confirmedReportChargingInformation{bound} | 
						reportChargingInformation  {bound}
						}
	ID					id-package-chargingInformation}

--  userInformation package --

userInformationPackage  {PARAMETERS-BOUND : bound} OPERATION-PACKAGE  ::= {
	CONSUMER INVOKES	{provideUserInformation  {bound} }
	ID					id-package-userInformation
	}

--  networkCapability package --

networkCapabilityPackage  {PARAMETERS-BOUND : bound} OPERATION-PACKAGE  ::= {
	CONSUMER INVOKES	{networkCapability  {bound}}
	ID					id-package-networkCapability
	}

--  chainedSCFOperation package --

chainedSCFOperationPackage {PARAMETERS-BOUND : bound} OPERATION-PACKAGE  ::= {
	CONSUMER INVOKES		{chainedHandlingInformationRequest  {bound} |
							chainedNotificationProvided {bound}|
							chainedConfirmedNotificationProvided {bound}|
							chainedReportChargingInformation {bound}|
							chainedConfirmedReportChargingInformation{bound}}
	SUPPLIER INVOKES		{chainedEstablishChargingRecord {bound}|
							chainedHandlingInformationResult {bound}|
							chainedNetworkCapability {bound}|
							chainedProvideUserInformation {bound}|
							chainedRequestNotification {bound}}
	ID						id-package-chainedSCFOperations
	}


-- abstract syntaxes --

scf-scfOperationsAbstractSyntax  ABSTRACT-SYNTAX  ::= {
	BasicSCF-SCF-PDUs
	IDENTIFIED BY				id-as-scf-scfOperationsAS}

BasicSCF-SCF-PDUs  ::= TCMessage {{SCF-SCF-Invokable}, {SCF-SCF-Returnable}}

SCF-SCF-Invokable {PARAMETERS-BOUND} OPERATION  ::= {
							activityTest | 
							establishChargingRecord {bound}| 
							confirmedNotificationProvided {bound}| 
							confirmedReportChargingInformation {bound} |  
							handlingInformationRequest {bound}| 
							handlingInformationResult {bound}| 
							networkCapability {bound}|
							notificationProvided {bound}|
							provideUserInformation {bound}| 
							reportChargingInformation {bound}| 
							requestNotification {bound}}

SCF-SCF-Returnable {PARAMETERS-BOUND}  OPERATION  ::= {
							activityTest | 
							establishChargingRecord {bound}| 
							confirmedNotificationProvided {bound}|
							confirmedReportChargingInformation {bound}| 
							handlingInformationRequest {bound}| 
							handlingInformationResult {bound}| 
							networkCapability {bound}|
							provideUserInformation {bound}| 
							requestNotification {bound}}


distributedSCFSystemAbstractSyntax  ABSTRACT-SYNTAX  ::= {
	BasicDSSP-PDUs
	IDENTIFIED BY				id-as-distributedSCFSystemAS}

BasicDSSP-PDUs  ::= TCMessage {{DSSP-Invokable}, {DSSP-Returnable}}

DSSP-Invokable {PARAMETERS-BOUND : bound} OPERATION  ::= {
							chainedHandlingInformationRequest {bound}|
							chainedNotificationProvided {bound}|
							chainedConfirmedNotificationProvided{bound} |
							chainedReportChargingInformation {bound}|
							chainedConfirmedReportChargingInformation {bound}}

DSSP-Returnable {PARAMETERS-BOUND : bound} OPERATION  ::= {
							chainedHandlingInformationRequest {bound}|
							chainedConfirmedNotificationProvided{bound} |
							chainedConfirmedReportChargingInformation {bound}}

distributedSCFBindingAbstractSyntax  ABSTRACT-SYNTAX   ::= {
									SCF-SCFBinding-PDUs{networkSpecificBoundSet}
	IDENTIFIED BY			id-as-scf-scfBindingAS}

SCF-SCFBinding-PDUs{PARAMETERS-BOUND : bound}  ::= CHOICE {
	bind					Bind {scfBind{bound}},
	unbind					Unbind {scfUnbind}
	}

END

IN-CS2-SCF-CUSF-ops-args {ccitt(0) identified-organization(4) etsi(0) inDomain(1) in-network(1) CS2(20) modules(0) in-cs2-scf-cusf-ops-args (15) version1(0)}

DEFINITIONS IMPLICIT TAGS ::= 
BEGIN
IMPORTS

	OPERATION
FROM Remote-Operations-Information-Objects ros-InformationObjects

	EXTENSION,
	PARAMETERS-BOUND,
	SupportedExtensions {}
FROM IN-CS2-classes classes

	opcode-initiateAssociation,
	opcode-releaseAssociation,
	opcode-requestReportBCUSMEvent,
	opcode-initialAssociationDP,
	opcode-connectAssociation,
	opcode-continueAssociation,
	opcode-eventReportBCUSM
FROM IN-CS2-operationcodes operationcodes

	BCUSMEvent,
	CalledPartyNumber {},
	Cause {},
	Duration,
	ExtensionField {},
	LegID,
	Message,
	MiscCallInfo,
	OperationCode
FROM IN-CS2-datatypes datatypes

	missingCustomerRecord,
	missingParameter,
	parameterOutOfRange,
	systemFailure,
	taskRefused,
	unexpectedComponentSequence,
	unexpectedDataValue,
	unexpectedParameter,
	unknownLegID
FROM IN-CS2-errortypes errortypes

	activityTest,
-- Direction: SCF --> CUSF, Timer: Tat 
-- This operation is used to check for the continued existence of a relationship between the SCF
-- and CUSF. If the relationship is still in existence, then the CUSF will respond. If no reply is
-- received, then the SCF will assume that the CUSF has failed in some way and will take the
-- appropriate action.

	reportUTSI,
-- Direction: CUSF --> SCF. Timer: Tru
-- This operation is issued by the CUSF in the context of the USI feature.  It is used to report the
-- receipt of a User to Service Information (UTSI) IE to the SCF.

	requestReportUTSI,
-- Direction: SCF --> CUSF. Timer: Trru
-- This operation is issued by the SCF in the context of the USI feature to request the CUSF to
-- monitor for a User to Service Information (UTSI) information element, which are received from a
-- user.

	sendSTUI,
-- Direction: SCF --> CUSF. Timer: Tss
-- This operation is issued by the SCF in the context of the USI feature. It is used to request the
-- CUSF to send a Service to User Information (STUI) information element to the indicated user.

FROM IN-CS2-SSF-SCF-ops-args {ccitt(0) identified-organization(4) etsi(0) inDomain(1) in-network(1) CS2(20) modules(0) in-cs2-ssf-scf-ops-args (5) version1(0)}

	classes, operationcodes, ros-InformationObjects, datatypes,errortypes
FROM IN-CS2-object-identifiers 
{ccitt(0) identified-organization(4) etsi(0) inDomain(1) in-network(1) CS2(20) modules(0) in-cs2-object-identifiers(17) version1(0)}

;

connectAssociation  {PARAMETERS-BOUND : bound}  OPERATION	::= {
	ARGUMENT		ConnectAssociationArg {bound}
	RETURN RESULT	FALSE
	ERRORS 			{missingParameter |
					parameterOutOfRange |
					systemFailure |
					taskRefused |
					unexpectedComponentSequence |
					unexpectedDataValue |
					unexpectedParameter}
	CODE			opcode-connectAssociation
	}
-- Direction: SCF-->CUSF, Timer: Tcoa
-- This operation is used to request the CUSF to proceed with processing. Additional information
-- which shall be used in further connection establishment is provided by the SCF.

ConnectAssociationArg  {PARAMETERS-BOUND : bound}::= SEQUENCE {
	address			[0]	CalledPartyNumber {bound},
	extensions		[1]	SEQUENCE SIZE(1..bound.&numOfExtensions) OF ExtensionField {bound}
																						OPTIONAL,
	...
	}

continueAssociation  {PARAMETERS-BOUND : bound}  OPERATION	::= {
	ARGUMENT		ContinueAssociationArg {bound}			OPTIONAL TRUE
	RETURN RESULT	FALSE
	ERRORS 			{missingParameter |
					parameterOutOfRange |
					systemFailure |
					taskRefused |
					unexpectedComponentSequence |
					unexpectedDataValue |
					unexpectedParameter}
	CODE			opcode-continueAssociation
	}
-- Direction: SCF-->CUSF, Timer: Tcona
-- This operation is used to request the CUSF to proceed with processing. Additional information
-- which is not related to further connection establishment may be  provided by the SCF.

ContinueAssociationArg  {PARAMETERS-BOUND : bound}::= SEQUENCE {
	extensions		[0]	SEQUENCE SIZE(1..bound.&numOfExtensions) OF
		      													ExtensionField {bound}	OPTIONAL,
	...
	}

eventReportBCUSM {PARAMETERS-BOUND : bound}  OPERATION	::= {
	ARGUMENT		EventReportBCUSMArg {bound}
	RETURN RESULT	FALSE
	ALWAYS RESPONDS	FALSE
	CODE			opcode-eventReportBCUSM
	}
-- Direction: CUSF --> SCF, Timer: Terbce
-- This operation is used to notify the SCF of a call unrelated event previously requested by the 
-- SCF in a RequestReportBCUSMEvent operation.

EventReportBCUSMArg  {PARAMETERS-BOUND : bound}::= SEQUENCE {
	eventTypeBCUSM					[0]	EventTypeBCUSM					OPTIONAL,
	eventSpecificInformationBCUSM	[1]	EventSpecificInformationBCUSM	OPTIONAL,
	miscCallInfo					[2]	MiscCallInfo				DEFAULT {messageType request},
	cUApplicationInd				[3]	CUApplicationInd				OPTIONAL,
	legID							[4] LegID							OPTIONAL,
	extensions						[5]	SEQUENCE SIZE(1..bound.&numOfExtensions) OF 
																ExtensionField {bound}	OPTIONAL,
	...
	}

initialAssociationDP  {PARAMETERS-BOUND : bound}  OPERATION	::= {
	ARGUMENT		InitialAssociationDPArg {bound}
	RETURN RESULT	FALSE
	ERRORS 			{missingCustomerRecord |
					missingParameter |
					parameterOutOfRange |
					systemFailure |
					taskRefused |
					unexpectedComponentSequence |
					unexpectedDataValue |
					unexpectedParameter}
	CODE			opcode-initialAssociationDP
	}
-- Direction: CUSF-->SCF, Timer: Tiadp
-- This operation is used after detection of a TDP to initiate a call unrelated association with the 
-- SCF.

InitialAssociationDPArg  {PARAMETERS-BOUND : bound}::= SEQUENCE {
	serviceKey				[0]	ServiceKey,
	cUApplicationInd		[1]	CUApplicationInd					OPTIONAL,
	miscCallInfo			[2]	MiscCallIinfo						OPTIONAL,
	eventtypeBCUSM			[3]	EventTypeBCUSM						OPTIONAL,
	calledPartyNumber		[4]	CalledPartyNumber {bound}			OPTIONAL,
	callingPartyNumber		[5]	CallingPartyNumber {bound}			OPTIONAL,
	callingPartySubAddress	[6]	CallingPartySubAddress				OPTIONAL,
	highLayerCompatibility	[7]	HighLayerCompatibility				OPTIONAL,
	bearerCapability		[8]	BearerCapability {bound}			OPTIONAL,
	uSIServiceIndicator		[9]	USIServiceIndicator {bound}			OPTIONAL,
	uSIInformation			[10] USIInformation {bound}				OPTIONAL,
	extensions				[11] SEQUENCE SIZE(1..bound.&numOfExtensions) OF
		  														ExtensionField {bound}	OPTIONAL,
	...
	}

initiateAssociation  {PARAMETERS-BOUND : bound}  OPERATION	::= {
	ARGUMENT		InitiateAssociationArg {bound}
	RETURN RESULT	TRUE
	ERRORS 			{missingParameter |
					parameterOutOfRange |
					systemFailure |
					taskRefused |
					unexpectedComponentSequence |
					unexpectedDataValue |
					unexpectedParameter}
	CODE		opcode-initiateAssociation
	}
-- Direction: SCF-->CUSF, Timer: Tia
-- This operation is used for allowing the SCF to initiate a call unrelated association with the 
-- user. The subsequent operations can be sent in the same TCAP message in the following order: 
-- 	- the RequestReportBCUSMEvent operation if an answer from the CUSF is expected

InitiateAssociationArg  {PARAMETERS-BOUND : bound}::= SEQUENCE {
	calledPartyNumber	[0]	CalledPartyNumber {bound},
	extensions			[1]	SEQUENCE SIZE(1..bound.&numOfExtensions) OF
		   												   ExtensionField {bound}	OPTIONAL,
	uSIServiceIndicator	[2]	USIServiceIndicator {bound}						OPTIONAL,
	uSIInformation		[3]	USIInformation {bound}							OPTIONAL,
	...
	}

releaseAssociation  {PARAMETERS-BOUND : bound}  OPERATION :: = {
	ARGUMENT		ReleaseAssociationArg {bound}
	RETURN RESULT	FALSE
	ALWAYS RESPONDS	FALSE
	CODE			opcode-releaseAssociation 
	}
--  Direction: SCF-->CUSF, Timer: Trel
--  This operation is used to indicate to the CUSF to release the existing association between the  
--  user and the network, during the BCUSM suspended at a DP.

ReleaseAssociationArg  {PARAMETERS-BOUND : bound}::= Cause {bound}

requestReportBCUSMEvent  {PARAMETERS-BOUND : bound}  OPERATION :: = {
	ARGUMENT		RequestReportBCUSMEventArg {bound}
	RETURN RESULT	FALSE
	ERRORS		 	{missingParameter |
					parameterOutOfRange |
					systemFailure |
					taskRefused |
					unknownLegID |
					unexpectedComponentSequence |
					unexpectedDataValue |
					unexpectedParameter}
	CODE			opcode-requestReportBCUSMEvent 
	}
-- Direction: SCF --> CUSF, Timer: Trrbce
-- This operation is used to request the CUSF to monitor a BCUSM DP.


RequestReportBCUSMEventArg  {PARAMETERS-BOUND : bound}::= SEQUENCE{
	bcusmEvents		[0] SEQUENCE SIZE(1..bound.&numOfBCUSMEvents) OF BCUSMEvent,
	monitorDuration	[3] Duration	OPTIONAL,
	extensions	 	[4] SEQUENCE SIZE(1..bound.&numOfExtensions) OF ExtensionField {bound}
																					OPTIONAL,
	cUDPCriteria	[5] CUApplicationInd											OPTIONAL,
	legID			[6] LegID														OPTIONAL,
	...
	}

END


IN-CS2-SCF-CUSF-pkgs-contracts-acs  {ccitt(0) identified-organization(4) etsi(0) inDomain(1) in-network(1) CS2(20) modules(0) in-cs2-scf-cusf-pkgs-contracts-acs (16) version1(0)}

DEFINITIONS :: =
BEGIN

-- This module describes the operation-packages, contracts and application-contexts used
-- over the SCF-CUSF interface.

IMPORTS

	emptyConnectionPackage,
	PARAMETERS-BOUND,
	networkSpecificBoundSet
FROM IN-CS2-classes classes


	CONTRACT, OPERATION-PACKAGE, OPERATION
FROM Remote-Operations-Information-Objects ros-InformationObjects

	TCMessage {} 
FROM TCAPMessages tc-Messages

	APPLICATION-CONTEXT, dialogue-abstract-syntax
FROM TC-Notation-Extensions tc-NotationExtensions

	releaseAssociation {},
	requestReportBCUSMEvent {},
	initiateAssociation {},
	connectAssociation {},
	continueAssociation {},
	eventReportBCUSM {},
	initialAssociationDP {}
FROM IN-CS2-SCF-CUSF-ops-args scf-cusf-Operations

	id-ac-cusf-scf,
	id-ac-scf-cusf,
	id-contract-scf-cusf,
	id-contract-cusf-scf,
	id-package-basic-cusf-scf,
	id-package-basic-scf-cusf,
	id-as-basic-cusf-scf,
	id-as-basic-scf-cusf,
	classes, ros-InformationObjects, tc-Messages, scf-cusf-Operations, tc-NotationExtensions,
	ssf-scf-Protocol, ssf-scf-Operations
FROM IN-CS2-object-identifiers {ccitt(0) identified-organization(4) etsi(0) inDomain(1) in-network(1) CS2(20) modules(0) in-cs2-object-identifiers (17) version1(0)}

	activityTestPackage,
	uSIHandlingPackage
FROM IN-CS2-SSF-SCF-pkgs-contracts-acs ssf-scf-Protocol 

	activityTest,
	reportUTSI,
	requestReportUTSI,
	sendSTUI
FROM IN-CS2-SSF-SCF-ops-args ssf-scf-Operations
;

-- application contexts --

cusf-scf-ac					APPLICATION-CONTEXT	::=	{
	CONTRACT					cusf-scf-contract
	DIALOGUE MODE				structured
	TERMINATION					basic
	ABSTRACT SYNTAXES			{dialogue-abstract-syntax | 
								cusf-scf-abstract-syntax}
	APPLICATION CONTEXT NAME	id-ac-cusf-scf}

scf-cusf-ac					APPLICATION-CONTEXT	::=	{
	CONTRACT					scf-cusf-contract
	DIALOGUE MODE				structured
	TERMINATION					basic
	ABSTRACT SYNTAXES			{dialogue-abstract-syntax | 
								scf-cusf-abstract-syntax}
	APPLICATION CONTEXT NAME	id-ac-scf-cusf}

-- contracts --

cusf-scf-contract			CONTRACT	::=	{
	CONNECTION				emptyConnectionPackage
	INITIATOR CONSUMER OF	{basic-cusf-scf-package {networkSpecificBoundSet}}
	RESPONDER CONSUMER OF	{activityTestPackage | 			
							uSIHandlingPackage {networkSpecificBoundSet}	
	ID						id-contract-scf-cusf}


scf-cusf-contract			CONTRACT	::=	{
	CONNECTION				emptyConnectionPackage
	INITIATOR CONSUMER OF	{basic-scf-cusf-package {networkSpecificBoundSet}|
							activityTestPackage | 
							uSIHandlingPackage {networkSpecificBoundSet}}
	ID						id-contract-cusf-scf}

-- basic cusf-scf package --

basic-cusf-scf-package		{PARAMETERS-BOUND : bound} OPERATION-PACKAGE	::=	{
	CONSUMER INVOKES		{eventReportBCUSM {bound} |
							initialAssociationDP {bound}}
	SUPPLIER INVOKES		{releaseAssociation {bound}|
							requestReportBCUSMEvent {bound} |
							connectAssociation {bound} |
							continueAssociation {bound}}
	ID						id-package-basic-cusf-scf}

--  basic scf-cusf package --

basic-scf-cusf-package		{PARAMETERS-BOUND : bound} OPERATION-PACKAGE	::=	{
	CONSUMER INVOKES		{initiateAssociation {bound}|
							releaseAssociation {bound}|
							requestReportBCUSMEvent {bound} |
							connectAssociation {bound} |
							continueAssociation {bound}}}
	SUPPLIER INVOKES		{eventReportBCUSM {bound}}
	ID						id-package-basic-scf-cusf}

-- abstract syntaxes --

cusf-scf-abstract-syntax		ABSTRACT-SYNTAX	::=	{
	BASIC-CUSF-SCF-PDUs
	IDENTIFIED BY			id-as-basic-cusf-scf}

BASIC-CUSF-SCF-PDUs	::= TCMessage {{CUSF-SCF-Invokable},{CUSF-SCF-Returnable}}

CUSF-SCF-Invokable	OPERATION	::= {
							activityTest|
							releaseAssociation  {networkSpecificBoundSet}|
							requestReportBCUSMEvent {networkSpecificBoundSet} |
							connectAssociation {networkSpecificBoundSet} |
							continueAssociation {networkSpecificBoundSet} |
							eventReportBCUSM {networkSpecificBoundSet} |
							initialAssociationDP {networkSpecificBoundSet} |
							reportUTSI {networkSpecificBoundSet} |
							requestReportUTSI {networkSpecificBoundSet} |
							sendSTUI {networkSpecificBoundSet}
							}

CUSF-SCF-Returnable	 OPERATION	::= {
						 	activityTest|
							requestReportBCUSMEvent {networkSpecificBoundSet} |
							connectAssociation {networkSpecificBoundSet} |
							continueAssociation {networkSpecificBoundSet} | 
							initialAssociationDP {networkSpecificBoundSet} | 
							requestReportUTSI {networkSpecificBoundSet} | 
							sendSTUI {networkSpecificBoundSet} 
							}

scf-cusf-abstract-syntax		ABSTRACT-SYNTAX	::=	{
	BASIC-SCF-CUSF-PDUs
	IDENTIFIED BY			id-as-basic-scf-cusf}

BASIC-SCF-CUSF-PDUs	::= TCMessage {{SCF-CUSF-Invokable},{SCF-CUSF-Returnable}}

SCF-CUSF-Invokable	OPERATION	::=	{
							activityTest|
							releaseAssociation  {networkSpecificBoundSet}|
							requestReportBCUSMEvent {networkSpecificBoundSet} |
							initiateAssociation  {networkSpecificBoundSet}|
							connectAssociation {networkSpecificBoundSet} |
							continueAssociation {networkSpecificBoundSet} |
							eventReportBCUSM {networkSpecificBoundSet} |
							reportUTSI {networkSpecificBoundSet} |
							requestReportUTSI {networkSpecificBoundSet} | 
							sendSTUI {networkSpecificBoundSet} 
							}
SCF-CUSF-Returnable	OPERATION	::= {
							activityTest|
							requestReportBCUSMEvent {networkSpecificBoundSet} |
							initiateAssociation  {networkSpecificBoundSet}|
							connectAssociation {networkSpecificBoundSet} |
							continueAssociation {networkSpecificBoundSet} | 
							requestReportUTSI {networkSpecificBoundSet} | 
							sendSTUI {networkSpecificBoundSet} 
							}

END

PARAMETER SEQUENCE {
	problem		[0] ENUMERATED {
						unknownOperation (0),
						tooLate (1),
						operationNotCancellable (2)},
	operation	[1] InvokeID
}
-- The operation failed to be canceled.

PARAMETER 	OPTIONALLY-PROTECTED {
			SET {problem [0] ExecutionProblem},
			COMPONENTS OF CommonResults},
			DIRQOP.&dirErrors-QOP{@dirqop}}
CODE		id-errcode-executionError}
ExecutionProblem::= INTEGER {
			missingInputValues (1),
			executionFailure (2)} 

PARAMETER ENUMERATED {
	unknownRequestedInfo(1),
	requestedInfoNotAvailable(2)
	-- other values not specified
	}

PARAMETER ENUMERATED {
	generic(0),
	unobtainable (1),
	congestion (2)
	}

PARAMETER
	FailureReason
FailureReason::= CHOICE {
	systemFailure	[0] UnavailableNetworkResource,
	scfTaskRefused 	[1] ScfTaskRefusedParameter,
	securityError 	[2] SET {
			problem 	[0] SecurityProblem,
			spkmInfo	[1] SPKM-ERROR
			}
	}

PARAMETER
	ScfTaskRefusedParameter
ScfTaskRefusedParameter ::= OPTIONALLY-PROTECTED {SEQUENCE {
		reason	ENUMERATED {
			generic(0),
			unobtainable (1),
			congestion(2)
			},
		securityParameters	[1] SecurityParameters	OPTIONAL 
	},
	SCFQOP.&scfErrorsQOP{@scfqop}
	}


[JMM1]this value to be confirmed (changing 3 to 50) - cf CAMEL. - Erfurt confirms 50 is OK. 04/01/99.
